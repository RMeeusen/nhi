FME workspace wrij_dwarsprofiel_gemeten.fmw

Parameters:
- DestDataset_ESRISHAPE = $(FME_MF_DIR)checks\wrij_dwarsprofiel_gemeten   # Destination Esri Shapefile Folder
- DestDataset_ESRISHAPE_3 = $(FME_MF_DIR)checks\wrij_dwarsprofiel_gemeten   # Destination Esri Shapefile Folder
- DestDataset_GML2 = G:\GIS WATERSYSTEEM\HyDAMO\FME\gml\wrij_dwarsprofiel_gemeten.gml   # Destination Geography Markup Language (GML) v2.1.2 File
- SourceDataset_ORACLE_RELATIONAL_3 = Blaeu   # Connection
- SourceDataset_ARCGIS_LAYER = X:\ArcGIS\Layer\Watersystemen\Beheerregister\Leidingvak (beheerregister watersystemen).lyr   # Source Esri ArcGIS Layer
- SourceDataset_ARCGIS_LAYER_6 = X:\ArcGIS\Layer\Watersystemen\Beheerregister\Dwarsprofiel (beheerregister watersystemen).lyr   # Source Esri ArcGIS Layer
- SourceDataset_ARCGIS_LAYER_5 = X:\ArcGIS\Layer\Watersystemen\Beheerregister\Dwarsprofielpunten (beheerregister watersystemen).lyr   # Source Esri ArcGIS Layer

Readers:
- ORACLE_RELATIONAL_2: ORACLE_RELATIONAL from $(SourceDataset_ORACLE_RELATIONAL_3)
- ARCGIS_LAYER_3: ARCGIS_LAYER from $(SourceDataset_ARCGIS_LAYER) in EPSG:28992
- ARCGIS_LAYER_4: ARCGIS_LAYER from $(SourceDataset_ARCGIS_LAYER_6) in EPSG:28992
- ARCGIS_LAYER_1: ARCGIS_LAYER from $(SourceDataset_ARCGIS_LAYER_5) in EPSG:28992

Writers:
- ESRISHAPE_1: ESRISHAPE to $(DestDataset_ESRISHAPE)
- ESRISHAPE_2: ESRISHAPE to $(DestDataset_ESRISHAPE_3)
- GML2_1: GML2 to $(DestDataset_GML2) in EPSG:28992

Dwarsprofiel (beheerregister watersystemen) (reader ARCGIS_LAYER_4)
    attributes: OBJECTID integer, PROIDENT char(24), DDPKRUIN float, DGPNUMME char(24), OPRRICHT integer, LBISTATG integer, DDPHWMAT float, PROSOORT integer, DDPHWGEM float, OPRDATOP date, DDPZMRPL float, GEGBRON char(50), DDPWNTPL float, OSMOMSCH char(60), DDPOPGPL float, DDPZETT float, TBTVWIND float, KTCSOORT integer, DDPRRGLF float, DDPITOGT float, DDPITOTO float, DDPTOORD integer, IWS_HYPERLINK char(240), RICHTING float, CREATED_USER char(50), CREATED_DATE date, LAST_EDITED_USER char(50), LAST_EDITED_DATE date, GEONAUWKEURIGHEID integer, ADMINNAUWKEURIGHEID integer,
      BETROUWBAARHEID integer, INWINNINGSWIJZE integer, INWINNINGSDATUM date, BRON char(255), IDEALISATIE integer, OPMERKINGEN char(255), GEONAUWKEURIGHEID_Z integer, IWS_KWLTGEO integer, IWS_EIGENAAR char(255), GLOBALID char(38), DDPIABKL integer, DDPITEEN integer, DDPPARAP integer, PRO_TYPE integer, MPN_MPN_ID guid, IPRKS_IPRKS_ID guid, SHAPE.LEN double
    -> AttributeRenamer
AttributeRenamer
    ATTR_TABLE = RENAME_SET_DEFAULT OBJECTID > dwarsprofiel
    -> AttributeCreator_2
AttributeCreator_2
    ATTR_TABLE = SET_TO datum_org = @Value(OPRDATOP)
    -> DateTimeConverter
DateTimeConverter
    OUT_FORMAT = %Y%m
    REPAIR_INPUT = NO
    DATETIME_ATTR = OPRDATOP
    -> Filter_intersects_candidate [Candidate]
    <REJECTED> -> DateTimeConverter__Rejected_
DateTimeConverter__Rejected_: Inspector
Leidingvak (beheerregister watersystemen) (reader ARCGIS_LAYER_3)
    attributes: OBJECTID integer, OVK_TYPE char(10), OVKIDENT char(24), AVVBODDR float, AVVWRHFC float, IWS_BESCHZONEBU float, IWS_BESCHZONEBI float, AVVBERMT integer, KWKSTATU integer, OVKSOORT integer, IWS_W_PLASBH_DL float, IWS_W_PLASBH_DR float, IWS_W_WATBRREFP float, IWS_W_WATPEIL float, IWS_W_INSTHGTEL float, IWS_W_INSTHGTER float, IWS_W_BRPLASBL float, IWS_W_BRPLASBR float, AVVZMRPL float, OSMOMSCH char(60), AVVWNTPL float, AVVDIEPT float, AVVSNELH float, AVVBODH float, AVVTALUL float, AVVTALUR float, AVVVERHG float, AVVNATOP float, AVVNATOM float, AVVHYDST float,
      AVVDROOB integer, AVVDROOE integer, IWS_EIND_AFSTAND integer, IWS_BEGIN_AFSTAND integer, AVVGEMBH float, AVVHOBOS float, AVVHOBES float, OVKLENGT integer, IWS_BREEDTE float, IWS_LENGTE double, IWS_LEGGERSTATUS integer, IWS_STATUSTEKST char(2000), IWS_MEMO char(2000), IWS_CATEGORIEEN integer, IWS_VAKTYPE integer, IWS_AVVHOBOS_L float, IWS_AVVHOBES_L float, IWS_TOEGANKELIJK integer, IWS_BOV_BR integer, AVVTALL2_L float, AVVTALR2_L float, AVVKNKL_L float, AVVKNKL2_L float, AVVKNKR_L float, AVVKNKR2_L float, IWS_OWASRTKN integer, RICHTING float, IWS_MAAIVELD_BOVENSTROOMS float, IWS_MAAIVELD_BENEDENSTROOMS float, IWS_BOVENBREEDTE_KANT_INSTEEK float,
      IWS_ZSTRAF integer, IWS_ZSTRAN integer, CREATED_USER char(50), CREATED_DATE date, LAST_EDITED_USER char(50), LAST_EDITED_DATE date, GEONAUWKEURIGHEID integer, ADMINNAUWKEURIGHEID integer, BETROUWBAARHEID integer, INWINNINGSWIJZE integer, INWINNINGSDATUM date, BRON char(255), IDEALISATIE integer, OPMERKINGEN char(255), GEONAUWKEURIGHEID_Z integer, IWS_KWLTGEO integer, IWS_EIGENAAR char(255), GLOBALID char(38), OHBLD_P1 integer, OHBLD_P2 integer, OHBLD_P3 integer, OHBLD_P4 integer, OHINR_TYPE integer, MOHINR_JJEVEN integer, MOHINR_JJONEVEN integer, MOHINR_STATUS integer, MOHINR_BIJZ_TXT char(50), MOHINR_BIJZ_LNG double, MOH_MUT_JAAR integer, STR_BLD_CODE integer,
      STR_BLD_DATE char(10), STR_BLD_OPMERK char(50), QSCAN_BLD_DATE char(10), QSCAN_BLD_TOETS integer, BOHINR_JJEVEN integer, BOHINR_JJONEVEN integer, BOHINR_STATUS integer, BOHINR_BIJZ_TXT char(50), BOHINR_BIJZ_LNG double, BOH_MUT_JAAR integer, AARD char(3), GEB_FUNCTIE char(2), OH_PAKKET char(6), OH_PAKKET_BASIS char(6), OH_BAGGERPL char(50), BAGCYCL integer, BOHINR_TYPE integer, LEG_ZIENSWIJZE integer, LEG_GEREED_VOOR_CL integer, IWS_W_PLASBTALL float, IWS_W_PLASBTALR float, IWS_CLASSIFICATIE_WATERVOERING integer, STEDELIJK_WATER_OVK integer, MIGRTYPE_KRW_VISMIG_NTW integer, COMBITYPE_KRW_VISMIG_NTW integer, IWS_GEOGRAFLIGGING integer, IWS_W_REFPEIL integer, NETWERK_ECOLOGIE integer, OWA_OWA_ID guid, OWM_OWM_ID guid,
      NETWERK_KRW_VISMIGRATIE integer, BAGGERTRANSPORT integer, WRIJ_AFVOER_EXTERN_OPGELEGD integer, WRIJ_AFVOER_HYDROVAK double, WRIJ_AFVOER_CUMULATIEF double, SHAPE.LEN double
    -> AttributeRangeFilter
AttributeRangeFilter
    IN_ATTR = KWKSTATU
    LUT = 101,399,use,400,699,dontuse,700,10000,use
    <UNFILTERED> -> AttributeRangeFilter__Unfiltered_
    use -> Filter_intersects_candidate [Filter]
    dontuse -> AttributeRangeFilter_dontuse
AttributeRangeFilter_dontuse: Inspector
AttributeRangeFilter__Unfiltered_: Inspector
Filter_intersects_candidate: SpatialFilter
    ATTR_CONFLICT_RES = Use Candidate
    CURVE_BOUNDARY_RULE_PARAM = Default Rule
    PREDATTR = _predicate
    AGGREGATE_HANDLING = Yes
    USE_BOUNDING_BOX = No
    BASE_TYPE = Multiple Filters
    PREDICATES = INTERSECTS
    PASS_CRITERIA = Pass Against One Filter
    ATTR_ACCUM_MODE = Merge Filter
    PASSED -> InlineQuerier_1 [Passed]
    PASSED -> Filter_intersects_candidate_Passed
    FAILED -> SpatialFilter_Failed
    <REJECTED> -> SpatialFilter__Rejected_
IQ_3_max_niet: Inspector
dwarsprofielen_houden_inlinequerier_3 (writer ESRISHAPE_1)
    attributes: max char(200), OBJECTID long, dwarsprofi char(200), OPRDATOP float, count char(200), PRW_PRW_ID long, IWS_LENGTE double, SHAPE_LEN double, GLOBALID char(38), PRO_PRO_ID char(200), IPRKS_IPRK char(254), _predicate char(200), PROIDENT char(24), OVKIDENT char(24), KWKSTATU long, datum_org char(200)
IQ_2_niet_max: Inspector
SpatialFilter_Failed: Inspector
Filter_intersects_candidate_Passed: Inspector
SpatialFilter__Rejected_: Inspector
Dwarsprofielpunten (beheerregister watersystemen) (reader ARCGIS_LAYER_1)
    attributes: OBJECTID integer, PBPIDENT char(24), PBPSOORT integer, IWS_TEKENCODE integer, IWS_TEKENNAAM char(255), IWS_VOLGNR integer, IWS_HOOGTE double, IWS_AFSTAND double, PRW_TYPE char(10), PRWIDENT char(40), PRO_PRO_ID char(38), OSMOMSCH char(60)
    -> InlineQuerier_4 [dwarsprofielpunten]
dwarsprofielpunten_op_profiel_NIEUW (writer ESRISHAPE_2)
    attributes: code long, objectbegi date, objecteind date, codevolgnr float, profielcod char(38), typeprofie float, ruwheidsty float, ruwheidsl float, ruwheidsh float, OBJECTID long, IWS_VOLGNR long, PRO_PRO_ID char(38), dwarsprofi char(200), GLOBALID char(38), OPRDATOP date, minimum char(200)
dwarsprofiel (writer GML2_1)
    attributes: code xml_buffer, statusobjectcode xml_char(18), objectbegintijd xml_buffer, objecteindtijd xml_buffer, administratiefgebied xml_buffer, codevolgnummer xml_int64, profielcode xml_buffer, typeprofielcode xml_char(9), ruwheidstypecode xml_char(15), ruwheidswaardelaag xml_real64, ruwheidswaardehoog xml_real64
AttributeCreator_Output_2: Inspector

Bookmark: (no name)
  Aanmaken van hoeveelheid profielen per datum per leidingvak. Dit wordt gedaan met sql code in de inlinequerier.
  Hier wordt de attribuut "count" aangemaakt. Deze telt het aantal profielen per datum in een  leidingvak.
InlineQuerier_1
    QUERY_DEF:
      output_3,select a.fme_feature_content, a.OBJECTID, a.GLOBALID, a.OPRDATOP, a.dwarsprofiel, a.PRW_PRW_ID, b.count from passed as a INNER JOIN (SELECT OBJECTID, OPRDATOP, count(OPRDATOP) as count from passed GROUP BY OBJECTID, OPRDATOP) b on a.OPRDATOP= b.OPRDATOP AND a.OBJECTID=b.OBJECTID;
      ,FIRST
    TABLE_DEF = Passed,OBJECTID,integer,GLOBALID,varchar(38),IWS_LENGTE,float,SHAPE_LEN,float,dwarsprofiel,varchar(200),PRO_PRO_ID,integer,PRW_PRW_ID,integer,OPRDATOP,text,IPRKS_IPRKS_ID,text,PROIDENT,varchar(24),_predicate,varchar(200)
    QUERY_SCHEMA = output_3,Passed.fme_feature_content,fme_feature_content,OBJECTID,integer,GLOBALID,varchar(38),OPRDATOP,text,dwarsprofiel,varchar(200),PRW_PRW_ID,integer,count,
    output_3 -> InlineQuerier_2 [output_3]

Bookmark: (no name)
  Hier worden de profielen welke niet het vaakst voorkomen(per datum) gefilterd. Er wordt een attribute aangemaakt: maxcount, deze geeft het maximale aantal profielen weer van een datum per leidingvak. Vervolgens wordt per leidingvak gekeken welke telling van data daarbij hoort. 
  Dus count=maxcount. 
  Wat hier overhouden is dus alle profielen waar de count gelijk is aan max count. Dit kan betekenen dat er meerdere reeksen per profiel nog overblijven. Er kunnen namelijk reeksen met hetzelfde aantal profielen zijn.
InlineQuerier_2
    QUERY_DEF = outout_4,select A.OBJECTID,A.GLOBALID, A.dwarsprofiel, A.OPRDATOP, A.count,a.fme_feature_content, B.max FROM output_3 A INNER JOIN (select OBJECTID, OPRDATOP, count, max(count) max from output_3 group by OBJECTID) B ON A.OBJECTID=B.OBJECTID AND A.count=B.max,FIRST,niet_max,select A.OBJECTID,A.GLOBALID, A.dwarsprofiel, A.OPRDATOP, A.count,a.fme_feature_content, B.max FROM output_3 A INNER JOIN (select OBJECTID, OPRDATOP, count, max(count) max from output_3 group by OBJECTID) B ON A.OBJECTID=B.OBJECTID AND A.count<>B.max,FIRST
    TABLE_DEF = output_3,OBJECTID,integer,GLOBALID,varchar(38),OPRDATOP,text,dwarsprofiel,varchar(200),PRW_PRW_ID,integer,PROIDENT,varchar(24),count,integer
    QUERY_SCHEMA = outout_4,OBJECTID,integer,GLOBALID,varchar(38),dwarsprofiel,varchar(200),OPRDATOP,text,count,integer,output_3.fme_feature_content,fme_feature_content,max,,niet_max,OBJECTID,integer,GLOBALID,varchar(38),dwarsprofiel,varchar(200),OPRDATOP,text,count,integer,output_3.fme_feature_content,fme_feature_content,max,
    outout_4 -> InlineQuerier_3 [outout_4]
    niet_max -> IQ_2_niet_max

Bookmark: (no name)
  Per leidingvak willen we uiteindelijk maar één datumreeks aan profielen. Als er meer dan 1 reeksen zijn, wordt gekeken welke het meest recent gemeten is, deze houden we uiteindelijk over. 
  Dit wordt ook gedaan met een sql code. Er wordt per leidingvak gekeken naar het meest recente datum en welke profielen daar vervolgens aan gelijk zijn. Hierdoor houden per leidingvak 1 profielreeks over van 1 datum.
InlineQuerier_3
    QUERY_DEF = goed,select b.max ,a.fme_feature_content ,a.* from "outout_4" a inner join (select objectid, max, max(oprdatop) maxdatum from outout_4 group by OBJECTID, max) b ON a.OBJECTID=b.OBJECTID AND a.oprdatop=b.maxdatum ,FIRST,max_niet,select b.max ,a.fme_feature_content ,a.* from "outout_4" a inner join (select objectid, max, max(oprdatop) maxdatum from outout_4 group by OBJECTID, max) b ON a.OBJECTID=b.OBJECTID AND a.oprdatop<>b.maxdatum AND a.count=b.max,FIRST
    TABLE_DEF = outout_4,OBJECTID,integer,dwarsprofiel,varchar(200),OPRDATOP,text,count,integer,max,integer,PRW_PRW_ID,integer,IWS_LENGTE,float,SHAPE_LEN,float,GLOBALID,varchar(38),PRO_PRO_ID,integer,IPRKS_IPRKS_ID,text,_predicate,varchar(200),PROIDENT,varchar(24)
    QUERY_SCHEMA = goed,max,integer,outout_4.fme_feature_content,fme_feature_content,OBJECTID,integer,dwarsprofiel,varchar(200),OPRDATOP,text,count,integer,PRW_PRW_ID,integer,IWS_LENGTE,float,SHAPE_LEN,float,GLOBALID,varchar(38),PRO_PRO_ID,integer,IPRKS_IPRKS_ID,text,_predicate,varchar(200),PROIDENT,varchar(24),max_niet,max,integer,outout_4.fme_feature_content,fme_feature_content,OBJECTID,integer,dwarsprofiel,varchar(200),OPRDATOP,text,count,integer,PRW_PRW_ID,integer,IWS_LENGTE,float,SHAPE_LEN,float,GLOBALID,varchar(38),PRO_PRO_ID,integer,IPRKS_IPRKS_ID,text,_predicate,varchar(200),PROIDENT,varchar(24)
    goed -> dwarsprofielen_houden_inlinequerier_3 (writer ESRISHAPE_1)
    goed -> InlineQuerier_4 [goed]
    max_niet -> IQ_3_max_niet

Bookmark: dwarsprofielpunten op profielen
  De dwarsprofielpunten zijn gekoppeld aan de dwarsprofielen d.m.v een globalid. Deze moet gelijk zijn. De data hiervoor staat in het attribuut globalid(Dwarsprofielen) en pro_pro_id (dwarsprofielpunten). Door middel van een sql code wordt hier gekeken waar de globalid=pro_pro_id.
InlineQuerier_4
    QUERY_DEF:
      biem,select a.fme_feature_content, a.OBJECTID, a.IWS_VOLGNR, a.PRO_PRO_ID, b.datum_org, b.dwarsprofiel, b.GLOBALID, b.OPRDATOP, b.PROIDENT, c.minimum
      from dwarsprofielpunten a, goed b
          inner join (select PRO_PRO_ID id, min(IWS_VOLGNR) minimum FROM dwarsprofielpunten GROUP BY id) c
              ON c.id=b.GLOBALID
              where b.globalid=a.pro_pro_id;,FIRST
    TABLE_DEF = dwarsprofielpunten,OBJECTID,integer,PBPIDENT,varchar(24),PBPSOORT,integer,IWS_TEKENCODE,integer,IWS_TEKENNAAM,varchar(255),IWS_VOLGNR,integer,IWS_HOOGTE,float,IWS_AFSTAND,float,PRW_TYPE,varchar(10),PRWIDENT,varchar(40),PRO_PRO_ID,varchar(38),OSMOMSCH,varchar(60),goed,OBJECTID,integer,GLOBALID,varchar(38),dwarsprofiel,varchar(200),PRW_PRW_ID,integer,count,integer,OPRDATOP,text,max_datum,varchar(200),max,varchar(200),SHAPE_LEN,float,hoogte_min,float,_predicate,varchar(200),PROIDENT,varchar(24),datum_org,text
    QUERY_SCHEMA = biem,dwarsprofielpunten.fme_feature_content,fme_feature_content,OBJECTID,integer,IWS_VOLGNR,integer,PRO_PRO_ID,varchar(38),datum_org,text,dwarsprofiel,varchar(200),GLOBALID,varchar(38),OPRDATOP,text,PROIDENT,varchar(24),minimum,
    biem -> AttributeCreator

Bookmark: volgnummer updaten
  Nu hebben we alle dwarsprofielpunten die op een dwarsprofiel liggen. Het probleem is alleen dat niet alle dwarsprofielen beginnen met een dwarsprofielpunten met volgnummer 1. Sommige dwarsprofielen beginnen met een dwarsprofielpunt met volgnummer 0 of 2. 
  Hier wordt per pro_pro_id (dus per dwarsprofiel) gekeken wat het minimale volgnummer is. Wanneer deze 0 is, wordt bij elk volgnummer op het profiel er +1 bij op gedaan. 
  Wanneer het minemale volgnunummer 2 is, wordt er -1 afgedaan.
AttributeCreator
    ATTR_TABLE:
      SET_TO code = @Value(OBJECTID)
      SET_TO objectbegintijd = @Value(datum_org)
      SET_TO objecteindtijd = @Value(datum_org)
      SET_TO codevolgnummer = FME_CONDITIONAL:DEFAULT_VALUE'@Value(IWS_VOLGNR)'BOOL_OP;OR;COMPOSITE_TEST;<Unused>;TEST @Value(minimum) = 0'@Evaluate(@Value(IWS_VOLGNR)+1)'BOOL_OP;OR;COMPOSITE_TEST;<Unused>;TEST @Value(minimum) = 2'@Evaluate(@Value(IWS_VOLGNR)-1)'FME_NUM_CONDITIONS3___
      SET_TO profielcode = @Value(PROIDENT)
      SET_TO typeprofielcode = waterloop
      SET_TO ruwheidstypecode = stricklerks
      SET_TO ruwheidswaardelaag = 25
      SET_TO ruwheidswaardehoog = 15
    -> dwarsprofielpunten_op_profiel_NIEUW (writer ESRISHAPE_2)
    -> AttributeCreator_Output_2
    -> dwarsprofiel (writer GML2_1)
