FME workspace HDSR_Hydamo_Afsluitmiddel.fmw

Parameters:
- SourceDataset_ORACLE_SPATIAL = Raadpleger_IRISPRD   # Connection
- DestDataset_GML2 = $(FME_MF_DIR)output\afsluitmiddel.gml   # Destination Geography Markup Language (GML) v2.1.2 File
- DestDataset_GML2_3 = $(FME_MF_DIR)output\sturing_afsluitmiddel.gml   # Destination Geography Markup Language (GML) v2.1.2 File

Readers:
- ORACLE_SPATIAL_1: ORACLE_SPATIAL from $(SourceDataset_ORACLE_SPATIAL)

Writers:
- GML2_1: GML2 to $(DestDataset_GML2) in EPSG:28992
- GML2_2: GML2 to $(DestDataset_GML2_3)

HYDROOBJECT (reader ORACLE_SPATIAL_1)
    attributes: OBJECTID number(38,0), CODE varchar2(50), NAAM varchar2(250), STATUSOBJECT number(5,0), SOORTOPPWATERKWANTITEIT number(5,0), CATEGORIEOPPWATERLICHAAM number(5,0), PERSISTENTIE number(5,0), WS_OND_DROOG number(5,0), WS_ONDH_NAT number(5,0), WS_ONDH_BG number(5,0), WS_ZANDSLOOT varchar2(1), DOSSIERMAP varchar2(15), IWS_W_WATPEIL number(38,8), IWS_W_WATBRREFP number(38,8), IWS_W_WATDIEPTE number(38,8), IWS_W_INSTHGTEL number(38,8), IWS_W_PLASBTALL number(38,8), IWS_W_BRPLASBL number(38,8), IWS_W_PLASBH_DL number(38,8), IWS_W_TALUDL number(38,8), IWS_W_BODBR number(38,8), IWS_W_BODHO number(38,8), WS_ONDERHOUDSMAAT number(38,8), WS_ONDERHOUDSDIEPTE number(38,8), IWS_W_TALUDR number(38,8), IWS_W_PLASBH_DR number(38,8), IWS_W_BRPLASBR number(38,8), IWS_W_PLASBTALR number(38,8), IWS_W_INSTHGTER number(38,8), OBJECTBEGINTIJD date,
      OBJECTEINDTIJD date, TIJDSTIPREGISTRATIE date, EINDREGISTRATIE date, NAAMSPACE varchar2(50), LOKAALID varchar2(50), LVPUBLICATIEDATUM date, DETAILNIVEAUGEOMETRIE number(38,8), WS_ONDH_VAAR varchar2(1), WS_SCHOUW varchar2(1), WS_MODEL varchar2(1), OPMERKING varchar2(500), WS_MAAI varchar2(1), LENGTE number(38,8), VISMIGRATIE varchar2(1), SE_ANNO_CAD_DATA blob
    -> AnchoredSnapper_4 [ANCHOR]
    -> AnchoredSnapper_2 [ANCHOR]
STUW (reader ORACLE_SPATIAL_1)
    attributes: STUWID number(38,0), CODE varchar2(50), NAAM varchar2(250), WS_CAWNR varchar2(60), STATUSOBJECT number(5,0), SOORTSTUW number(5,0), HYPERLINK varchar2(500), WS_DOSSIERMAP varchar2(15), DOORSTROOMBREEDTE number(38,8), KRUINBREEDTE number(38,8), LAAGSTEDOORSTROOMHOOGTE number(38,8), HOOGSTEDOORSTROOMHOOGTE number(38,8), SOORTREGELBAARHEID number(5,0), HOOGTECONSTRUCTIE number(38,8), SOORTMATERIAAL number(5,0), OPMERKING varchar2(500), WS_BEHEERDER number(5,0), OBJECTBEGINTIJD date, OBJECTEINDTIJD date, TIJDSTIPREGISTRATIE date, EINDREGISTRATIE date, NAAMSPACE varchar2(50), LOKAALID varchar2(50), LVPUBLICATIEDATUM date, DETAILNIVEAUGEOMETRIE number(38,8), RICHTING number(38,8), WS_ONDERDEELWATERKERING varchar2(1), WS_AFSLUITWIJZE_KERING number(5,0), WS_ONDERDEEL_CALAMITEITENPLAN varchar2(1), SE_ANNO_CAD_DATA blob,
      WS_GEW_ONDH number(5,0), WS_BTNGEW_ONDH number(5,0)
    -> AttributeKeeper_4
AttributeManager_3_Output: Inspector
AFSLUITMIDDEL (reader ORACLE_SPATIAL_1)
    attributes: OBJECTID number(38,0), CODE varchar2(50), NAAM varchar2(250), WS_CAWNR varchar2(50), STATUSOBJECT number(5,0), SOORTAFSLUITMIDDEL number(5,0), FUNCTIEAFSLUITMIDDEL number(5,0), TYPEMATERIAALAFSLUITMIDDEL number(5,0), SOORTREGELBAARHEID number(5,0), HOOGTEOPENING number(38,8), BREEDTEOPENING number(38,8), WS_VORMOPENING number(5,0), WS_VORMAFSLUITMIDDEL number(5,0), HYPERLINK varchar2(500), WS_DOSSIERMAP varchar2(500), OPMERKING varchar2(500), WS_BEHEERDER number(5,0), WS_GEW_ONDH number(5,0), WS_BTNGEW_ONDH number(5,0), RICHTING number(38,8), OBJECTBEGINTIJD date, OBJECTEINDTIJD date, TIJDSTIPREGISTRATIE date, EINDREGISTRATIE date, NAAMSPACE varchar2(50), LOKAALID varchar2(50), LVPUBLICATIEDATUM date, DETAILNIVEAUGEOMETRIE number(38,8), DREMPELPEIL number(38,8), SIGNALERINGSPEIL number(38,8),
      SLUITPEIL number(38,8), OPENKEERPEIL number(38,8), OPENINGSPEIL number(38,8), WATERKERINGID number(5,0), WS_WATERKERINGCODE varchar2(50), WS_DUIKERSIFONHEVELCODE varchar2(50), WS_COUPURECODE varchar2(50), WS_GEMAALCODE varchar2(50), WS_SLUISCODE varchar2(50), WS_STUWCODE varchar2(50), SE_ANNO_CAD_DATA blob, DUIKERSIFONHEVELID number(10,0), COUPURE_ID number(10,0), GEMAAL_ID number(10,0), SLUIS_ID number(10,0), STUW_ID number(10,0)
    -> AttributeManager
AnchoredSnapper_2_Snapped: Inspector
AnchoredSnapper_2_Untouched: Inspector
afsluitmiddel (writer GML2_1)
    attributes: code xml_char(200), codegerelateerdobject xml_char(200), statusobjectcode xml_char(200), objectbegintijd xml_char(200), objecteindtijd xml_char(200), soortafsluitmiddelcode xml_char(200), soortregelbaarheidcode xml_char(200), breedte xml_char(200), hoogte xml_char(200), minimalehoogtebovenkant xml_char(200), maximalehoogtebovenkant xml_char(200), afvoercoefficient xml_char(200), NAAM xml_char(250)
sturing_afsluitmiddel (writer GML2_2)
    attributes: code xml_char(200), codegerelateerdobject xml_char(200), statusobjectcode xml_char(200), objectbegintijd xml_char(200), objecteindtijd xml_char(200), complexesturingcode xml_char(200), hyperlink xml_char(200), geldigbegintijd xml_char(200), geldigeindtijd xml_char(200), stuurvariabelecode xml_char(200), doelvariabelecode xml_char(200), streefwaarde xml_char(200), bovenmarge xml_char(200), ondermarge xml_char(200), sturingtypecode xml_char(200)
AttributeManager_11_Output: Inspector

Bookmark: Attribuutnamen goed zetten en default waarden invullen
AttributeKeeper_4
    KEEP_ATTRS = DOORSTROOMBREEDTE,LAAGSTEDOORSTROOMHOOGTE,RICHTING,SOORTSTUW,STATUSOBJECT,HOOGSTEDOORSTROOMHOOGTE,OBJECTEINDTIJD,KRUINBREEDTE,NAAM,WS_CAWNR,CODE,HYPERLINK,OBJECTBEGINTIJD,SOORTREGELBAARHEID
    -> AttributeCreator_9
AttributeCreator_9
    ATTR_TABLE:
      SET_TO laagstedoorstroombreedte
      SET_TO hoogstedoorstroombreedte
      SET_TO afvoercoefficient = FME_CONDITIONAL:DEFAULT_VALUE'_FME_NO_OP_'BOOL_OP;OR;COMPOSITE_TEST;<Unused>;TEST @Value(SOORTREGELBAARHEID) = 1'1.7'FME_NUM_CONDITIONS2___
      SET_TO administratiefgebiedcode = 17
      SET_TO statusobjectcode = FME_CONDITIONAL:DEFAULT_VALUE'@Evaluate(@Value(STATUSOBJECT)/100)'BOOL_OP;COMPOSITE;COMPOSITE_TEST;1;TEST @Value(STATUSOBJECT) = 9900'98'FME_NUM_CONDITIONS2___
      SET_TO soortstuwcode = @Value(SOORTSTUW)
      SET_TO soortregelbaarheidcode = @Value(SOORTREGELBAARHEID)
    -> AttributeRenamer_2
AttributeRenamer_2
    ATTR_TABLE:
      RENAME_SET_DEFAULT CODE > code
      RENAME_SET_DEFAULT DOORSTROOMBREEDTE > doorstroombreedte
      RENAME_SET_DEFAULT HOOGSTEDOORSTROOMHOOGTE > hoogstedoorstroomhoogte
      RENAME_SET_DEFAULT NAAM > naam
      RENAME_SET_DEFAULT OBJECTBEGINTIJD > objectbegintijd
      RENAME_SET_DEFAULT OBJECTEINDTIJD > objecteindtijd
      RENAME_SET_DEFAULT LAAGSTEDOORSTROOMHOOGTE > laagstedoorstroomhoogte
      RENAME_SET_DEFAULT HYPERLINK > hyperlink
      RENAME_SET_DEFAULT KRUINBREEDTE > kruinbreedte
    -> AnchoredSnapper_4 [CANDIDATE]
AttributeManager
    ATTR_TABLE:
      SET_TO code = @Value(CODE)
      SET_TO codegerelateerdobject = FME_CONDITIONAL:DEFAULT_VALUE'_FME_NO_OP_'BOOL_OP;OR;COMPOSITE_TEST;<Unused>;TEST @Value(GEMAAL_ID) ATTRIBUTE_HAS_VALUE _FME_BLANK_STRING_'@Value(GEMAAL_ID)'BOOL_OP;OR;COMPOSITE_TEST;<Unused>;TEST @Value(COUPURE_ID) ATTRIBUTE_HAS_VALUE _FME_BLANK_STRING_'@Value(COUPURE_ID)'BOOL_OP;OR;COMPOSITE_TEST;<Unused>;TEST @Value(SLUIS_ID) ATTRIBUTE_HAS_VALUE _FME_BLANK_STRING_'@Value(SLUIS_ID)'BOOL_OP;OR;COMPOSITE_TEST;<Unused>;TEST @Value(STUW_ID) ATTRIBUTE_HAS_VALUE _FME_BLANK_STRING_'@Value(STUW_ID)'BOOL_OP;OR;COMPOSITE_TEST;<Unused>;TEST @Value(WS_DUIKERSIFONHEVELCODE) ATTRIBUTE_HAS_VALUE _FME_BLANK_STRING_'@Value(WS_DUIKERSIFONHEVELCODE)'FME_NUM_CONDITIONS6___
      SET_TO statusobjectcode = FME_CONDITIONAL:DEFAULT_VALUE'@Evaluate(@Value(STATUSOBJECT)/100)'BOOL_OP;OR;COMPOSITE_TEST;<Unused>;TEST @Value(STATUSOBJECT) = 9900'98'FME_NUM_CONDITIONS2___
      SET_TO objectbegintijd = @Value(OBJECTBEGINTIJD)
      SET_TO objecteindtijd = @Value(OBJECTEINDTIJD)
      SET_TO soortafsluitmiddelcode = @Value(SOORTAFSLUITMIDDEL)
      SET_TO soortregelbaarheidcode = @Value(SOORTREGELBAARHEID)
      SET_TO breedte = @Value(BREEDTEOPENING)
      SET_TO hoogte = @Value(HOOGTEOPENING)
      SET_TO minimalehoogtebovenkant
      SET_TO maximalehoogtebovenkant
      SET_TO afvoercoefficient
      REMOVE OBJECTID
      REMOVE CODE
      REMOVE WS_CAWNR
      REMOVE STATUSOBJECT
      REMOVE SOORTAFSLUITMIDDEL
      REMOVE FUNCTIEAFSLUITMIDDEL
      REMOVE TYPEMATERIAALAFSLUITMIDDEL
      REMOVE SOORTREGELBAARHEID
      REMOVE HOOGTEOPENING
      REMOVE BREEDTEOPENING
      REMOVE WS_VORMOPENING
      REMOVE WS_VORMAFSLUITMIDDEL
      REMOVE HYPERLINK
      REMOVE WS_DOSSIERMAP
      REMOVE OPMERKING
      REMOVE WS_BEHEERDER
      REMOVE WS_GEW_ONDH
      REMOVE WS_BTNGEW_ONDH
      REMOVE RICHTING
      REMOVE OBJECTBEGINTIJD
      REMOVE OBJECTEINDTIJD
      REMOVE TIJDSTIPREGISTRATIE
      REMOVE EINDREGISTRATIE
      REMOVE NAAMSPACE
      REMOVE LOKAALID
      REMOVE LVPUBLICATIEDATUM
      REMOVE DETAILNIVEAUGEOMETRIE
      REMOVE DREMPELPEIL
      REMOVE SIGNALERINGSPEIL
      REMOVE SLUITPEIL
      REMOVE OPENKEERPEIL
      REMOVE OPENINGSPEIL
      REMOVE WATERKERINGID
      REMOVE WS_WATERKERINGCODE
      REMOVE WS_DUIKERSIFONHEVELCODE
      REMOVE WS_COUPURECODE
      REMOVE WS_GEMAALCODE
      REMOVE WS_SLUISCODE
      REMOVE WS_STUWCODE
      REMOVE SE_ANNO_CAD_DATA
      REMOVE DUIKERSIFONHEVELID
      REMOVE COUPURE_ID
      REMOVE GEMAAL_ID
      REMOVE SLUIS_ID
      REMOVE STUW_ID
    -> AnchoredSnapper_2 [CANDIDATE]

Bookmark: Stuwen snappen op de waterlopen
AnchoredSnapper_4
    CLEANING_TOLERANCE_MODE = AUTO
    SNAPTYPE_PARAM = Segment Snapping
    TOLERANCE = 0.1
    SNAPPED -> TestFilter_2
    UNTOUCHED -> TestFilter_2

Bookmark: Opsplitsen stuwen met afsluitmiddel en overige stuwen
TestFilter_2
    DEFAULT_VALUE = <UNFILTERED>
    TEST_LIST:
      BOOL_OP,OR,COMPOSITE_TEST,<Unused>,TEST_CLAUSE,"TEST @Value(soortstuwcode) = 1
      TEST @Value(soortstuwcode) = 2
      TEST @Value(soortstuwcode) = 3
      TEST @Value(soortstuwcode) = 4
      TEST @Value(soortstuwcode) = 9
      TEST @Value(soortstuwcode) = 12
      TEST @Value(soortstuwcode) = 13
      TEST @Value(soortstuwcode) = 21
      TEST @Value(soortstuwcode) = 22
      TEST @Value(soortstuwcode) = 23
      TEST @Value(soortstuwcode) = 23",met afsluitmiddel
    met afsluitmiddel -> Cloner_4

Bookmark: Afluitmiddelen van stuwen creeren
Cloner_4
    COPIES = 1
    COPYATT = _copynum
    COPY -> AttributeManager_2
Note: Bij soortstuwcode 3 (stuw met klep) soortafsluitmiddelcode 7 (stuwklep) ingevuld omdat nieuwe optie stuwklep is toegevoegd in de keuzelijst. / Nog aanpassen in beschrijving van datamodel HyDAMO
AttributeManager_2
    ATTR_TABLE:
      SET_TO codegerelateerdobject = @Value(code)
      SET_TO soortafsluitmiddelcode = FME_CONDITIONAL:DEFAULT_VALUE'98'BOOL_OP;OR;COMPOSITE_TEST;<Unused>;TEST @Value(soortstuwcode) = 1'2'BOOL_OP;OR;COMPOSITE_TEST;<Unused>;TEST @Value(soortstuwcode) = 2'4'BOOL_OP;OR;COMPOSITE_TEST;<Unused>;TEST @Value(soortstuwcode) = 3'7'FME_NUM_CONDITIONS4___
      RENAME_SET_VALUE doorstroombreedte > breedte
      SET_TO hoogte
      RENAME_SET_VALUE laagstedoorstroomhoogte > minimalehoogtebovenkant
      RENAME_SET_VALUE hoogstedoorstroomhoogte > maximalehoogtebovenkant
      REMOVE naam
      REMOVE laagstedoorstroombreedte
      REMOVE hoogstedoorstroombreedte
      REMOVE administratiefgebiedcode
      REMOVE WS_CAWNR
      REMOVE STATUSOBJECT
      REMOVE SOORTSTUW
      REMOVE SOORTREGELBAARHEID
      REMOVE RICHTING
      REMOVE _copynum
      REMOVE hyperlink
      REMOVE kruinbreedte
    -> StringPadder
StringPadder
    BLANK_ATTRIBUTE = No
    PADCHAR = AM_
    SIDE = Left
    SRC_ATTRS = code
    WIDTH = 7
    -> AttributeManager_3
AttributeManager_3
    ATTR_TABLE = REMOVE soortstuwcode
    -> afsluitmiddel (writer GML2_1)
    -> AttributeManager_3_Output

Bookmark: Afsluitmiddelen snappen op de waterlopen
AnchoredSnapper_2
    CLEANING_TOLERANCE_MODE = AUTO
    SNAPTYPE_PARAM = Segment Snapping
    TOLERANCE = 0.1
    SNAPPED -> DatabaseJoiner
    SNAPPED -> AnchoredSnapper_2_Snapped
    SNAPPED -> afsluitmiddel (writer GML2_1)
    UNTOUCHED -> DatabaseJoiner
    UNTOUCHED -> AnchoredSnapper_2_Untouched
    UNTOUCHED -> afsluitmiddel (writer GML2_1)

Bookmark: Sturing toevoegen, waarden toekennen o.b.v. CAW
Note: Streefpeilen uit CAW export, marges verzonnen
DatabaseJoiner
    ADDED_FIELDS = TagOmschrijving Waarde
    ATTR_ACCUM_MODE = Merge Joined
    ATTR_CONFLICT_RES = Use Original
    CSV2_CASE_SENSITIVE_FIELD_NAMES = Yes
    CSV2_DATA_START_LINE = 2
    CSV2_DELIMITER = ;
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_READ_SKIPPED_LINES = No
    CSV2_SCAN_ADDITIONAL_FIELDS = No
    CSV2_SCAN_MAX_ROWS = 1000
    CSV2_SCAN_TYPES = No
    CSV2_SCHEMA = LocId,string,NO;LocOmschrijving,string,YES;AppGroepId,string,NO;AppGroepOmschrijving,string,NO;InfoBlokType,string,NO;InfoblokOmschrijving,string,NO;IBvolgnr,string,NO;TagId,string,NO;TagOmschrijving,string,YES;Adres,string,NO;GegType,string,NO;GegTypeAfkorting,string,NO;MinGebruiker,string,NO;MaxGebruiker,string,NO;Eenheid,string,NO;Waarde,string,YES;Kwaliteit,string,NO;Tijdstip,string,NO
    CSV2_SKIP_DUPLICATE_DELIMITERS = No
    CSV2_TRIM_FIELD_NAME_QUALIFIERS = Yes
    CSV2_TRIM_FIELD_VALUE_QUALIFIERS = Yes
    CSV2_USE_CUSTOM_SCHEMA = YES
    DATASET = H:\DATA\Service\EPKE\TKI D-Hydro\20171002_AllIeInstellingen.csv
    FORMAT = CSV2
    JOIN_KEYS = NAAM LocOmschrijving
    MATCH_MULTIPLE_DISPLAY = Create a feature for each match
    MATCH_RULE_DISPLAY = Match All (1:M)
    TABLE = CSV
    JOINED -> Tester
Tester
    BOOL_OP = OR
    TEST_CLAUSE:
      TEST @Value(TagOmschrijving) = Streefpeil
      TEST @Value(TagOmschrijving) = Streefbenedenpeil
      TEST @Value(TagOmschrijving) = Streefbovenpeil
    PASSED -> AttributeManager_11
AttributeManager_11
    ATTR_TABLE:
      SET_TO code = sturing_@Value(code)
      REMOVE TagOmschrijving
      REMOVE _matched_records
      REMOVE soortafsluitmiddelcode
      REMOVE soortregelbaarheidcode
      REMOVE breedte
      REMOVE hoogte
      REMOVE minimalehoogtebovenkant
      REMOVE maximalehoogtebovenkant
      REMOVE afvoercoefficient
      REMOVE NAAM
      SET_TO complexesturingcode = n
      SET_TO hyperlink
      SET_TO geldigbegintijd
      SET_TO geldigeindtijd
      SET_TO stuurvariabelecode = 2
      SET_TO doelvariabelecode = 1
      SET_TO streefwaarde = @Value(Waarde)
      SET_TO bovenmarge = 0.05
      SET_TO ondermarge = -0.05
      SET_TO sturingtypecode = 1
      REMOVE Waarde
    -> AttributeManager_11_Output
    -> sturing_afsluitmiddel (writer GML2_2)
