FME workspace HDSR_Hydamo_Stuw.fmw

Parameters:
- SourceDataset_ORACLE_SPATIAL = Raadpleger_IRISPRD   # Connection
- DestDataset_GML2 = $(FME_MF_DIR)output\stuw.gml   # Destination Geography Markup Language (GML) v2.1.2 File
- DestDataset_GML2_4 = $(FME_MF_DIR)output\sturing_stuw.gml   # Destination Geography Markup Language (GML) v2.1.2 File

Readers:
- ORACLE_SPATIAL_1: ORACLE_SPATIAL from $(SourceDataset_ORACLE_SPATIAL)

Writers:
- GML2_1: GML2 to $(DestDataset_GML2) in EPSG:28992
- GML2_2: GML2 to $(DestDataset_GML2_4)

AnchoredSnapper_4_Snapped: Inspector
AnchoredSnapper_4_Untouched: Inspector
stuw (writer GML2_1)
    attributes: code xml_char(200), naam xml_char(200), statusobjectcode xml_char(200), objectbegintijd xml_char(200), objecteindtijd xml_char(200), hyperlink xml_char(200), soortstuwcode xml_char(200), soortregelbaarheidcode xml_char(200), laagstedoorstroombreedte xml_char(200), hoogstedoorstroombreedte xml_char(200), kruinbreedte xml_char(200), laagstedoorstroomhoogte xml_char(200), hoogstedoorstroomhoogte xml_char(200), afvoercoefficient xml_char(200), administratiefgebiedcode xml_char(200)
sturing_stuw (writer GML2_2)
    attributes: code xml_char(200), codegerelateerdobject xml_char(200), statusobjectcode xml_char(200), objectbegintijd xml_char(200), objecteindtijd xml_char(200), complexesturingcode xml_char(200), geldigbegintijd xml_char(200), geldigeindtijd xml_char(200), stuurvariabelecode xml_char(200), doelvariabelecode xml_char(200), streefwaarde xml_char(200), bovenmarge xml_char(200), ondermarge xml_char(200), sturingtypecode xml_char(200)
AttributeManager_11_Output: Inspector

Bookmark: Inlezen waterlopen en stuwen
HYDROOBJECT (reader ORACLE_SPATIAL_1)
    attributes: OBJECTID number(38,0), CODE varchar2(50), NAAM varchar2(250), STATUSOBJECT number(5,0), SOORTOPPWATERKWANTITEIT number(5,0), CATEGORIEOPPWATERLICHAAM number(5,0), PERSISTENTIE number(5,0), WS_OND_DROOG number(5,0), WS_ONDH_NAT number(5,0), WS_ONDH_BG number(5,0), WS_ZANDSLOOT varchar2(1), DOSSIERMAP varchar2(15), IWS_W_WATPEIL number(38,8), IWS_W_WATBRREFP number(38,8), IWS_W_WATDIEPTE number(38,8), IWS_W_INSTHGTEL number(38,8), IWS_W_PLASBTALL number(38,8), IWS_W_BRPLASBL number(38,8), IWS_W_PLASBH_DL number(38,8), IWS_W_TALUDL number(38,8), IWS_W_BODBR number(38,8), IWS_W_BODHO number(38,8), WS_ONDERHOUDSMAAT number(38,8), WS_ONDERHOUDSDIEPTE number(38,8), IWS_W_TALUDR number(38,8), IWS_W_PLASBH_DR number(38,8), IWS_W_BRPLASBR number(38,8), IWS_W_PLASBTALR number(38,8), IWS_W_INSTHGTER number(38,8), OBJECTBEGINTIJD date,
      OBJECTEINDTIJD date, TIJDSTIPREGISTRATIE date, EINDREGISTRATIE date, NAAMSPACE varchar2(50), LOKAALID varchar2(50), LVPUBLICATIEDATUM date, DETAILNIVEAUGEOMETRIE number(38,8), WS_ONDH_VAAR varchar2(1), WS_SCHOUW varchar2(1), WS_MODEL varchar2(1), OPMERKING varchar2(500), WS_MAAI varchar2(1), LENGTE number(38,8), VISMIGRATIE varchar2(1), SE_ANNO_CAD_DATA blob
    -> AnchoredSnapper_4 [ANCHOR]
STUW (reader ORACLE_SPATIAL_1)
    attributes: STUWID number(38,0), CODE varchar2(50), NAAM varchar2(250), WS_CAWNR varchar2(60), STATUSOBJECT number(5,0), SOORTSTUW number(5,0), HYPERLINK varchar2(500), WS_DOSSIERMAP varchar2(15), DOORSTROOMBREEDTE number(38,8), KRUINBREEDTE number(38,8), LAAGSTEDOORSTROOMHOOGTE number(38,8), HOOGSTEDOORSTROOMHOOGTE number(38,8), SOORTREGELBAARHEID number(5,0), HOOGTECONSTRUCTIE number(38,8), SOORTMATERIAAL number(5,0), OPMERKING varchar2(500), WS_BEHEERDER number(5,0), OBJECTBEGINTIJD date, OBJECTEINDTIJD date, TIJDSTIPREGISTRATIE date, EINDREGISTRATIE date, NAAMSPACE varchar2(50), LOKAALID varchar2(50), LVPUBLICATIEDATUM date, DETAILNIVEAUGEOMETRIE number(38,8), RICHTING number(38,8), WS_ONDERDEELWATERKERING varchar2(1), WS_AFSLUITWIJZE_KERING number(5,0), WS_ONDERDEEL_CALAMITEITENPLAN varchar2(1), SE_ANNO_CAD_DATA blob,
      WS_GEW_ONDH number(5,0), WS_BTNGEW_ONDH number(5,0)
    -> AttributeCreator

Bookmark: Attribuutnamen goed zetten en default waarden invullen
AttributeCreator
    ATTR_TABLE:
      SET_TO laagstedoorstroombreedte = @Value(DOORSTROOMBREEDTE)
      SET_TO hoogstedoorstroombreedte = @Value(DOORSTROOMBREEDTE)
      SET_TO statusobjectcode = FME_CONDITIONAL:DEFAULT_VALUE'@Evaluate(@Value(STATUSOBJECT)/100)'BOOL_OP;OR;COMPOSITE_TEST;<Unused>;TEST @Value(STATUSOBJECT) = 9900'98'FME_NUM_CONDITIONS2___
      SET_TO soortstuwcode = @Value(SOORTSTUW)
      SET_TO soortregelbaarheidcode = FME_CONDITIONAL:DEFAULT_VALUE'_FME_NO_OP_'BOOL_OP;OR;COMPOSITE_TEST;<Unused>;TEST @Value(SOORTREGELBAARHEID) = 1'3'BOOL_OP;OR;COMPOSITE_TEST;<Unused>;TEST @Value(SOORTREGELBAARHEID) = 2'2'BOOL_OP;OR;COMPOSITE_TEST;<Unused>;TEST @Value(SOORTREGELBAARHEID) = 3'4'BOOL_OP;OR;COMPOSITE_TEST;<Unused>;TEST @Value(SOORTREGELBAARHEID) = 4'1'BOOL_OP;OR;COMPOSITE_TEST;<Unused>;TEST @Value(SOORTREGELBAARHEID) = 99'99'FME_NUM_CONDITIONS6___
      SET_TO afvoercoefficient = FME_CONDITIONAL:DEFAULT_VALUE'_FME_NO_OP_'BOOL_OP;OR;COMPOSITE_TEST;<Unused>;TEST @Value(SOORTREGELBAARHEID) = 1;TEST @Value(SOORTREGELBAARHEID) = 2'1.7'FME_NUM_CONDITIONS2___
      SET_TO administratiefgebiedcode = 17
    -> NullAttributeMapper
NullAttributeMapper
    ATTRCHOICE = Selected Attributes
    ATTRLIST = soortstuwcode
    NEW_VALUE = 99
    NULL_TREATMENT = New Value
    SOURCE_ATTR_VAL = Null
    -> AttributeManager
AttributeManager
    ATTR_TABLE:
      REMOVE STUWID
      RENAME_SET_VALUE CODE > code
      RENAME_SET_VALUE NAAM > naam
      REMOVE WS_CAWNR
      REMOVE STATUSOBJECT
      RENAME_SET_VALUE OBJECTBEGINTIJD > objectbegintijd
      RENAME_SET_VALUE OBJECTEINDTIJD > objecteindtijd
      RENAME_SET_VALUE HYPERLINK > hyperlink
      REMOVE SOORTSTUW
      REMOVE SOORTREGELBAARHEID
      REMOVE WS_DOSSIERMAP
      REMOVE DOORSTROOMBREEDTE
      RENAME_SET_VALUE KRUINBREEDTE > kruinbreedte
      RENAME_SET_VALUE LAAGSTEDOORSTROOMHOOGTE > laagstedoorstroomhoogte
      RENAME_SET_VALUE HOOGSTEDOORSTROOMHOOGTE > hoogstedoorstroomhoogte
      REMOVE HOOGTECONSTRUCTIE
      REMOVE SOORTMATERIAAL
      REMOVE OPMERKING
      REMOVE WS_BEHEERDER
      REMOVE TIJDSTIPREGISTRATIE
      REMOVE EINDREGISTRATIE
      REMOVE NAAMSPACE
      REMOVE LOKAALID
      REMOVE LVPUBLICATIEDATUM
      REMOVE DETAILNIVEAUGEOMETRIE
      REMOVE RICHTING
      REMOVE WS_ONDERDEELWATERKERING
      REMOVE WS_AFSLUITWIJZE_KERING
      REMOVE WS_ONDERDEEL_CALAMITEITENPLAN
      REMOVE SE_ANNO_CAD_DATA
      REMOVE WS_GEW_ONDH
      REMOVE WS_BTNGEW_ONDH
    -> AnchoredSnapper_4 [CANDIDATE]

Bookmark: Stuwen snappen op de waterlopen
AnchoredSnapper_4
    CLEANING_TOLERANCE_MODE = AUTO
    SNAPTYPE_PARAM = Segment Snapping
    TOLERANCE = 0.1
    SNAPPED -> Tester_9
    SNAPPED -> stuw (writer GML2_1)
    SNAPPED -> AnchoredSnapper_4_Snapped
    UNTOUCHED -> Tester_9
    UNTOUCHED -> stuw (writer GML2_1)
    UNTOUCHED -> AnchoredSnapper_4_Untouched

Bookmark: Opsplitsen automatische stuwen en overige stuwen
Tester_9
    BOOL_OP = OR
    TEST_CLAUSE:
      TEST @Value(soortregelbaarheidcode) = 2
      TEST @Value(soortregelbaarheidcode) = 3
    PASSED -> AttributeManager_3

Bookmark: Attributen toevoegen voor sturing
AttributeManager_3
    ATTR_TABLE = SET_TO codegerelateerdobject = @Value(code)
    -> AttributeManager_6
AttributeManager_6
    ATTR_TABLE:
      SET_TO code = sturing_@Value(code)
      SET_TO complexesturingcode = n
      SET_TO hyperlink
      SET_TO geldigbegintijd
      SET_TO geldigeindtijd
      SET_TO stuurvariabelecode = 1
      SET_TO doelvariabelecode = 1
      SET_TO streefwaarde
      SET_TO bovenmarge
      SET_TO ondermarge
      SET_TO sturingtypecode = 1
      REMOVE administratiefgebiedcode
      REMOVE hyperlink
      REMOVE soortstuwcode
      REMOVE soortregelbaarheidcode
      REMOVE laagstedoorstroombreedte
      REMOVE hoogstedoorstroombreedte
      REMOVE kruinbreedte
      REMOVE laagstedoorstroomhoogte
      REMOVE hoogstedoorstroomhoogte
      REMOVE afvoercoefficient
    -> DatabaseJoiner

Bookmark: Waarden toekennen o.b.v. CAW
Note: Streefpeilen uit CAW export, marges verzonnen
DatabaseJoiner
    ADDED_FIELDS = TagOmschrijving Waarde
    ATTR_ACCUM_MODE = Merge Joined
    ATTR_CONFLICT_RES = Use Original
    CSV2_CASE_SENSITIVE_FIELD_NAMES = Yes
    CSV2_DATA_START_LINE = 2
    CSV2_DELIMITER = ;
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_READ_SKIPPED_LINES = No
    CSV2_SCAN_ADDITIONAL_FIELDS = No
    CSV2_SCAN_MAX_ROWS = 1000
    CSV2_SCAN_TYPES = No
    CSV2_SCHEMA = LocId,string,NO;LocOmschrijving,string,YES;AppGroepId,string,NO;AppGroepOmschrijving,string,NO;InfoBlokType,string,NO;InfoblokOmschrijving,string,NO;IBvolgnr,string,NO;TagId,string,NO;TagOmschrijving,string,YES;Adres,string,NO;GegType,string,NO;GegTypeAfkorting,string,NO;MinGebruiker,string,NO;MaxGebruiker,string,NO;Eenheid,string,NO;Waarde,string,YES;Kwaliteit,string,NO;Tijdstip,string,NO
    CSV2_SKIP_DUPLICATE_DELIMITERS = No
    CSV2_TRIM_FIELD_NAME_QUALIFIERS = Yes
    CSV2_TRIM_FIELD_VALUE_QUALIFIERS = Yes
    CSV2_USE_CUSTOM_SCHEMA = YES
    DATASET = H:\DATA\Service\EPKE\TKI D-Hydro\20171002_AllIeInstellingen.csv
    FORMAT = CSV2
    JOIN_KEYS = naam LocOmschrijving
    MATCH_MULTIPLE_DISPLAY = Create a feature for each match
    MATCH_RULE_DISPLAY = Match All (1:M)
    TABLE = CSV
    JOINED -> Tester
Tester
    BOOL_OP = OR
    TEST_CLAUSE:
      TEST @Value(TagOmschrijving) = Streefpeil
      TEST @Value(TagOmschrijving) = Streefbenedenpeil
      TEST @Value(TagOmschrijving) = Streefbovenpeil
    PASSED -> AttributeManager_11
AttributeManager_11
    ATTR_TABLE:
      SET_TO streefwaarde = @Value(Waarde)
      SET_TO bovenmarge = 0.05
      SET_TO ondermarge = -0.05
      REMOVE naam
      REMOVE TagOmschrijving
      REMOVE Waarde
      REMOVE _matched_records
    -> sturing_stuw (writer GML2_2)
    -> AttributeManager_11_Output

FME custom transformer UnconditionalFeatureMerger
This transformer is a wrapper around the FeatureMerger, configuring it to merge all incoming requestors with supplier attributes. Optionally, it can be configured to process duplicate suppliers.
Please note that the UncoditionalFeatureMerger may be deprecated in the near future, as the FeatureMerger now allows unconditional merging via constant values for the join.
Input ports:
    Requestor
Receives the new attributes/geometry from the features connected to the Supplier port.
    Supplier
The source of new attributes/geometry for features that enter through the Requestor port. If Process Duplicate suppliers is off, only the first Supplier will be used.
    Output ports:
    Merged
Requestors that find a Supplier. In the case of unconditional merging, this should be all Requestors.
    Referenced
Suppliers that are found by at least one Requestor.
    Note: A Supplier may still be output through this port even though none of its attributes were merged. This can occur because all of the attributes were already present in the Requestor or were provided by earlier Suppliers.
    DuplicateSupplier
Extra Supplier features. Note that duplicate Suppliers will only be output if Process Duplicate Suppliers is set to No. If Process Duplicate Suppliers is set to Yes, then duplicate Suppliers will be output via the Referenced port.

Parameters:
- PROCESS_DUPS = No   # Process Duplicate Suppliers

Requestor (input)
    -> FeatureMerger [REQUESTOR]
Supplier (input)
    -> FeatureMerger [SUPPLIER]
FeatureMerger
    GEOM_TYPE = Build Polygons
    IGNORE_NULLS = Yes
    JOIN_KEYS = 1 1 AUTO
    MERGE_TYPE = Attributes Only
    PROCESS_DUPS = $(PROCESS_DUPS)
    SUPPLIERS_FIRST = No
    SUPPLIER_PREFIX_DUMMY = YES
    MERGED -> Merged (output)
    REFERENCED -> Referenced (output)
    DUPLICATE_SUPPLIER -> DuplicateSupplier (output)
Merged (output)
Referenced (output)
DuplicateSupplier (output)
