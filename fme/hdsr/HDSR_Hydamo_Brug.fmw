FME workspace HDSR_Hydamo_Brug.fmw

Parameters:
- SourceDataset_ORACLE_SPATIAL = Raadpleger_IRISPRD   # Connection
- SourceDataset_ORACLE_SPATIAL_3 = Raadpleger_IRISPRD   # Connection
- DestDataset_GML2 = $(FME_MF_DIR)output\brug.gml   # Destination Geography Markup Language (GML) v2.1.2 File

Readers:
- ORACLE_SPATIAL_1: ORACLE_SPATIAL from $(SourceDataset_ORACLE_SPATIAL)
- ORACLE_SPATIAL_2: ORACLE_SPATIAL from $(SourceDataset_ORACLE_SPATIAL_3)

Writers:
- GML2_1: GML2 to $(DestDataset_GML2)

HYDROOBJECT (reader ORACLE_SPATIAL_1)
    attributes: OBJECTID number(38,0), CODE varchar2(50), NAAM varchar2(250), STATUSOBJECT number(5,0), SOORTOPPWATERKWANTITEIT number(5,0), CATEGORIEOPPWATERLICHAAM number(5,0), PERSISTENTIE number(5,0), WS_OND_DROOG number(5,0), WS_ONDH_NAT number(5,0), WS_ONDH_BG number(5,0), WS_ZANDSLOOT varchar2(1), DOSSIERMAP varchar2(15), IWS_W_WATPEIL number(38,8), IWS_W_WATBRREFP number(38,8), IWS_W_WATDIEPTE number(38,8), IWS_W_INSTHGTEL number(38,8), IWS_W_PLASBTALL number(38,8), IWS_W_BRPLASBL number(38,8), IWS_W_PLASBH_DL number(38,8), IWS_W_TALUDL number(38,8), IWS_W_BODBR number(38,8), IWS_W_BODHO number(38,8), WS_ONDERHOUDSMAAT number(38,8), WS_ONDERHOUDSDIEPTE number(38,8), IWS_W_TALUDR number(38,8), IWS_W_PLASBH_DR number(38,8), IWS_W_BRPLASBR number(38,8), IWS_W_PLASBTALR number(38,8), IWS_W_INSTHGTER number(38,8), OBJECTBEGINTIJD date,
      OBJECTEINDTIJD date, TIJDSTIPREGISTRATIE date, EINDREGISTRATIE date, NAAMSPACE varchar2(50), LOKAALID varchar2(50), LVPUBLICATIEDATUM date, DETAILNIVEAUGEOMETRIE number(38,8), WS_ONDH_VAAR varchar2(1), WS_SCHOUW varchar2(1), WS_MODEL varchar2(1), OPMERKING varchar2(500), WS_MAAI varchar2(1), LENGTE number(38,8), VISMIGRATIE varchar2(1), SE_ANNO_CAD_DATA blob
    -> Reprojector_2
Reprojector_2
    DEST = EPSG:28992
    INTERPOLATION_TYPE_NAME = Nearest Neighbor
    RASTER_CELL_SIZE = Preserve Cells
    RASTER_TOLERANCE = 0.0
    SOURCE = Read from feature
    REPROJECTED -> AnchoredSnapper [ANCHOR]
BRUG (reader ORACLE_SPATIAL_2)
    attributes: OBJECTID number(38,0), CODE varchar2(24), NAAM varchar2(50), STATUSLEGGERWATERSYSTEEM number(5,0), HYPERLINK varchar2(100), OPMERKING varchar2(400), SOORTOVERSPANNING number(5,0), HOOGTEONDERZIJDE number(38,8), DOORVAARTBREEDTE number(38,8), WS_DOORVAARTLENGTE number(38,8), HOOGTECONSTRUCTIE number(38,8), SOORTMATERIAAL number(5,0), WS_BEWEEGBAREBRUG varchar2(1), WS_MATERIAALPIJLERS number(5,0), WS_AANTALPIJLERS number(38,0), WS_AANTALONDERDOORGANGEN number(38,0), TYPEKRUISING number(5,0), WS_DOSSIERMAP varchar2(25), WS_BOUWJAAR varchar2(4), RICHTING number(38,8), GLOBALID varchar2(38), TIJDSTIPREGISTRATIE timestamp, OBJECTBEGINTIJD timestamp, OBJECTEINDTIJD timestamp, NAMESPACE varchar2(50), DETAILNIVEAUGEOMETRIE number(38,8), LVPUBLICATIEDATUM timestamp, METADATAID number(38,0), SE_ANNO_CAD_DATA blob, STATUSOBJECT number(5,0),
      WATERKERINGID number(38,0), WS_WATERKERINGCODE varchar2(50), WS_DOORSTROOMBREEDTE number(38,8)
    -> GeometryFilter
GeometryFilter
    BREAK_AGG = Yes
    GEOM_PORT_NAMES = Point
    INSTANTIATE = No
    POINT -> AttributeManager
    POINT -> GeometryFilter_Point
    <UNFILTERED> -> GeometryFilter__Unfiltered_
Note: aannames voor ruwheid en verliezen
AttributeManager
    ATTR_TABLE:
      REMOVE OBJECTID
      RENAME_SET_VALUE CODE > code
      RENAME_SET_VALUE NAAM > naam
      RENAME_SET_VALUE STATUSOBJECT > statusobjectcode = FME_CONDITIONAL:DEFAULT_VALUE'@Evaluate(@Value(statusobjectcode)/100)'BOOL_OP;OR;COMPOSITE_TEST;<Unused>;TEST @Value(statusobjectcode) = 9900;TEST @Value(statusobjectcode) = 201;TEST statusobjectcode ATTRIBUTE_VALUE_NULL _FME_BLANK_STRING_'98'FME_NUM_CONDITIONS2___
      RENAME_SET_VALUE OBJECTBEGINTIJD > objectbegintijd
      RENAME_SET_VALUE OBJECTEINDTIJD > objecteindtijd
      REMOVE STATUSLEGGERWATERSYSTEEM
      RENAME_SET_VALUE HYPERLINK > hyperlink
      REMOVE OPMERKING
      REMOVE SOORTOVERSPANNING
      RENAME_SET_VALUE HOOGTEONDERZIJDE > hoogteonderzijde
      SET_TO hoogtebovenzijde
      REMOVE DOORVAARTBREEDTE
      RENAME_SET_VALUE WS_DOORVAARTLENGTE > lengte
      SET_TO ruwheidstypecode = 4
      SET_TO ruwheidswaarde = 75
      SET_TO intreeverlies = 0.6
      SET_TO uittreeverlies = 1
      SET_TO administratiefgebiedcode = 17
      REMOVE HOOGTECONSTRUCTIE
      REMOVE SOORTMATERIAAL
      REMOVE WS_BEWEEGBAREBRUG
      REMOVE WS_MATERIAALPIJLERS
      REMOVE WS_AANTALPIJLERS
      REMOVE WS_AANTALONDERDOORGANGEN
      REMOVE TYPEKRUISING
      REMOVE WS_DOSSIERMAP
      REMOVE WS_BOUWJAAR
      REMOVE RICHTING
      REMOVE GLOBALID
      REMOVE TIJDSTIPREGISTRATIE
      REMOVE NAMESPACE
      REMOVE DETAILNIVEAUGEOMETRIE
      REMOVE LVPUBLICATIEDATUM
      REMOVE METADATAID
      REMOVE SE_ANNO_CAD_DATA
      REMOVE WATERKERINGID
      REMOVE WS_WATERKERINGCODE
      REMOVE WS_DOORSTROOMBREEDTE
    -> Reprojector
Reprojector
    DEST = EPSG:28992
    INTERPOLATION_TYPE_NAME = Nearest Neighbor
    RASTER_CELL_SIZE = Preserve Cells
    RASTER_TOLERANCE = 0.0
    SOURCE = Read from feature
    REPROJECTED -> AnchoredSnapper [CANDIDATE]
AnchoredSnapper
    CLEANING_TOLERANCE_MODE = AUTO
    SNAPTYPE_PARAM = Segment Snapping
    TOLERANCE = 0.25
    SNAPPED -> AnchoredSnapper_Snapped
    SNAPPED -> brug (writer GML2_1)
    UNTOUCHED -> AnchoredSnapper_Untouched
    UNTOUCHED -> brug (writer GML2_1)
AnchoredSnapper_Snapped: Inspector
brug (writer GML2_1)
    attributes: code xml_char(200), naam xml_char(200), statusobjectcode xml_char(200), objectbegintijd xml_char(200), objecteindtijd xml_char(200), hyperlink xml_char(200), hoogteonderzijde xml_char(200), hoogtebovenzijde xml_char(200), lengte xml_char(200), ruwheidstypecode xml_char(200), ruwheidswaarde xml_char(200), intreeverlies xml_char(200), uittreeverlies xml_char(200), administratiefgebiedcode xml_char(200)
AnchoredSnapper_Untouched: Inspector
GeometryFilter_Point: Inspector
GeometryFilter__Unfiltered_: Inspector
