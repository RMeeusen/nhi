FME workspace HDSR_Hydamo_DuikerSifonHevel.fmw

Parameters:
- DestDataset_SHAPE_5 = \\SRVSOBEK\Hydrologie\HGK\Onderhoud\HDBow_GIV   # Destination Esri Shape Directory
- SourceDataset_ORACLE_SPATIAL_6 = Raadpleger_IRISPRD   # Connection
- DestDataset_GML2 = $(FME_MF_DIR)output\duikersifonhevel.gml   # Destination Geography Markup Language (GML) v2.1.2 File

Readers:
- ORACLE_SPATIAL_1: ORACLE_SPATIAL from $(SourceDataset_ORACLE_SPATIAL_6)

Writers:
- SHAPE_1: SHAPE to $(DestDataset_SHAPE_5)
- GML2_1: GML2 to $(DestDataset_GML2) in EPSG:28992

AnchoredSnapper_2
    SNAPTYPE_PARAM = Segment Snapping
    TOLERANCE = 0.25
    SNAPPED -> duikersifonhevel (writer GML2_1)
    SNAPPED -> AnchoredSnapper_2_Snapped
    UNTOUCHED -> AnchoredSnapper_2_Untouched
    UNTOUCHED -> duikersifonhevel (writer GML2_1)
AnchoredSnapper_2_Snapped: Inspector
duikersifonhevel (writer GML2_1)
    attributes: OBJECTID xml_decimal(38,0), CODE xml_char(50), NAAM xml_char(250), STATUSOBJECT xml_int32, SOORTOPPWATERKWANTITEIT xml_int32, CATEGORIEOPPWATERLICHAAM xml_int32, PERSISTENTIE xml_int32, WS_OND_DROOG xml_int32, WS_ONDH_NAT xml_int32, WS_ONDH_BG xml_int32, WS_ZANDSLOOT xml_char(1), DOSSIERMAP xml_char(15), IWS_W_WATPEIL xml_decimal(38,8), IWS_W_WATBRREFP xml_decimal(38,8), IWS_W_WATDIEPTE xml_decimal(38,8), IWS_W_INSTHGTEL xml_decimal(38,8), IWS_W_PLASBTALL xml_decimal(38,8), IWS_W_BRPLASBL xml_decimal(38,8), IWS_W_PLASBH_DL xml_decimal(38,8), IWS_W_TALUDL xml_decimal(38,8), IWS_W_BODBR xml_decimal(38,8), IWS_W_BODHO xml_decimal(38,8), WS_ONDERHOUDSMAAT xml_decimal(38,8), WS_ONDERHOUDSDIEPTE xml_decimal(38,8), IWS_W_TALUDR xml_decimal(38,8), IWS_W_PLASBH_DR xml_decimal(38,8), IWS_W_BRPLASBR xml_decimal(38,8), IWS_W_PLASBTALR xml_decimal(38,8), IWS_W_INSTHGTER xml_decimal(38,8), OBJECTBEGINTIJD xml_char(20),
      OBJECTEINDTIJD xml_char(20), TIJDSTIPREGISTRATIE xml_char(20), EINDREGISTRATIE xml_char(20), NAAMSPACE xml_char(50), LOKAALID xml_char(50), LVPUBLICATIEDATUM xml_char(20), DETAILNIVEAUGEOMETRIE xml_decimal(38,8), WS_ONDH_VAAR xml_char(1), WS_SCHOUW xml_char(1), WS_MODEL xml_char(1), OPMERKING xml_char(500), WS_MAAI xml_char(1), LENGTE xml_decimal(38,8), VISMIGRATIE xml_char(1), SE_ANNO_CAD_DATA xml_buffer, code xml_char(200), statusobjectcode xml_char(200), objectbegintijd xml_char(200), objecteindtijd xml_char(200), hyperlink xml_char(200), indpeilregulpeilscheidend xml_char(200), lengte xml_char(200), hoogteopening xml_char(200), breedteopening xml_char(200), hoogtebinnenonderkantbenedenstrooms xml_char(200), hoogtebinnenonderkantbovenstrooms xml_char(200), vormkokercode xml_char(200), soortkokervormigeconstructiecode xml_char(200), ruwheidstypecode xml_char(200), ruwheidswaarde xml_char(200),
      intreeverlies xml_char(200), aantalknikken xml_char(200), uittreeverlies xml_char(200), administratiefgebiedcode xml_char(200)
AnchoredSnapper_2_Untouched: Inspector

Bookmark: Inlezen brondata uit beheerregister
DUIKERSIFONHEVEL_LIJN (reader ORACLE_SPATIAL_1)
    attributes: OBJECTID number(38,0), CODE varchar2(50), WS_NAAM varchar2(250), WS_OSMOMSCH varchar2(60), STATUSOBJECT number(5,0), VORMKOKER number(5,0), INDPEILREGULPEILSCHEIDEND varchar2(1), LENGTE number(38,8), HOOGTEOPENING number(38,8), BREEDTEOPENING number(38,8), HOOGTEBOKBES number(38,8), HOOGTEBOKBOS number(38,8), SOORTMATERIAAL number(5,0), SOORTKRUISING number(5,0), HYPERLINK varchar2(500), WS_DOSSIERMAP varchar2(500), OPMERKING varchar2(500), WS_BEHEERDER number(5,0), WS_GEW_ONDH number(5,0), WS_BTNGEW_ONDH number(5,0), OBJECTBEGINTIJD date, OBJECTEINDTIJD date, TIJDSTIPREGISTRATIE date, EINDREGISTRATIE date, NAAMSPACE varchar2(50), LOKAALID varchar2(50), LVPUBLICATIEDATUM date, DETAILNIVEAUGEOMETRIE number(38,8), DREMPELPEIL number(38,8), SIGNALERINGSPEIL number(38,8),
      SLUITPEIL number(38,8), OPENKEERPEIL number(38,8), OPENINGSPEIL number(38,8), WATERKERINGID number(5,0), WS_WATERKERINGCODE varchar2(50), WS_ONDERDEEL_CALAMITEITENPLAN varchar2(1), SE_ANNO_CAD_DATA blob
    -> AttributeKeeper_3
    -> FeatureMerger_4 [SUPPLIER]
DUIKERSIFONHEVEL_PUNT (reader ORACLE_SPATIAL_1)
    attributes: OBJECTID number(38,0), WS_DUIKERSIFONHEVELCODE varchar2(50), RICHTING number(38,8), SE_ANNO_CAD_DATA blob, DUIKERSIFONHEVEL_ID_KOPIE number(10,0), DUIKERSIFONHEVEL_ID number(10,0)
    -> FeatureMerger_4 [REQUESTOR]
    -> FeatureMerger_5 [SUPPLIER]
HYDROOBJECT (reader ORACLE_SPATIAL_1)
    attributes: OBJECTID number(38,0), CODE varchar2(50), NAAM varchar2(250), STATUSOBJECT number(5,0), SOORTOPPWATERKWANTITEIT number(5,0), CATEGORIEOPPWATERLICHAAM number(5,0), PERSISTENTIE number(5,0), WS_OND_DROOG number(5,0), WS_ONDH_NAT number(5,0), WS_ONDH_BG number(5,0), WS_ZANDSLOOT varchar2(1), DOSSIERMAP varchar2(15), IWS_W_WATPEIL number(38,8), IWS_W_WATBRREFP number(38,8), IWS_W_WATDIEPTE number(38,8), IWS_W_INSTHGTEL number(38,8), IWS_W_PLASBTALL number(38,8), IWS_W_BRPLASBL number(38,8), IWS_W_PLASBH_DL number(38,8), IWS_W_TALUDL number(38,8), IWS_W_BODBR number(38,8), IWS_W_BODHO number(38,8), WS_ONDERHOUDSMAAT number(38,8), WS_ONDERHOUDSDIEPTE number(38,8), IWS_W_TALUDR number(38,8), IWS_W_PLASBH_DR number(38,8), IWS_W_BRPLASBR number(38,8), IWS_W_PLASBTALR number(38,8), IWS_W_INSTHGTER number(38,8), OBJECTBEGINTIJD date,
      OBJECTEINDTIJD date, TIJDSTIPREGISTRATIE date, EINDREGISTRATIE date, NAAMSPACE varchar2(50), LOKAALID varchar2(50), LVPUBLICATIEDATUM date, DETAILNIVEAUGEOMETRIE number(38,8), WS_ONDH_VAAR varchar2(1), WS_SCHOUW varchar2(1), WS_MODEL varchar2(1), OPMERKING varchar2(500), WS_MAAI varchar2(1), LENGTE number(38,8), VISMIGRATIE varchar2(1), SE_ANNO_CAD_DATA blob
    -> AnchoredSnapper_2 [ANCHOR]
    -> SpatialFilter_2 [Filter]
    -> AnchoredSnapper_3 [ANCHOR]

Bookmark: Omzetten naar HyDAMO format
Note: Behouden noodzakelijke velden
AttributeKeeper_3
    KEEP_ATTRS = BREEDTEOPENING,SOORTMATERIAAL,HOOGTEOPENING,INDPEILREGULPEILSCHEIDEND,OBJECTBEGINTIJD,SOORTKRUISING,HOOGTEBOKBOS,OBJECTEINDTIJD,STATUSOBJECT,VORMKOKER,CODE,LENGTE,HOOGTEBOKBES,HYPERLINK
    -> AttributeRenamer_3
Note: Hernoemen attributenamen
AttributeRenamer_3
    ATTR_TABLE:
      RENAME_SET_DEFAULT HOOGTEBOKBES > hoogtebinnenonderkantbenedenstrooms
      RENAME_SET_DEFAULT HOOGTEBOKBOS > hoogtebinnenonderkantbovenstrooms
      RENAME_SET_DEFAULT SOORTKRUISING > soortkokervormigeconstructiecode
      RENAME_SET_DEFAULT STATUSOBJECT > statusobjectcode
      RENAME_SET_DEFAULT INDPEILREGULPEILSCHEIDEND > indpeilregulpeilscheidend
      RENAME_SET_DEFAULT CODE > code
      RENAME_SET_DEFAULT VORMKOKER > vormcode
      RENAME_SET_DEFAULT LENGTE > lengte
      RENAME_SET_DEFAULT HOOGTEOPENING > hoogteopening
      RENAME_SET_DEFAULT BREEDTEOPENING > breedteopening
      RENAME_SET_DEFAULT SOORTMATERIAAL > soortmateriaal
      RENAME_SET_DEFAULT HYPERLINK > hyperlink
      RENAME_SET_DEFAULT OBJECTBEGINTIJD > objectbegintijd
      RENAME_SET_DEFAULT OBJECTEINDTIJD > objecteindtijd
    -> AttributeCreator_4
Note: Hier worden default aannames / gemaakt. Let op, nog geen tabel voor / ruwheden obv materiaal gemaakt
Note: Toevoegen noodzakelijk attributen en maken van aannames
AttributeCreator_4
    ATTR_TABLE:
      SET_TO ruwheidstypecode = 4
      SET_TO ruwheidswaarde = 75
      SET_TO intreeverlies = FME_CONDITIONAL:DEFAULT_VALUE'0.6'BOOL_OP;OR;COMPOSITE_TEST;<Unused>;TEST @Value(vormcode)@ = 1'0.6'BOOL_OP;OR;COMPOSITE_TEST;<Unused>;TEST @Value(vormcode) = 3'0.5'BOOL_OP;OR;COMPOSITE_TEST;<Unused>;TEST @Value(vormcode) = 4'0.6'BOOL_OP;OR;COMPOSITE_TEST;<Unused>;TEST @Value(vormcode) = 5'0.6'BOOL_OP;OR;COMPOSITE_TEST;<Unused>;TEST @Value(vormcode) = 6'0.6'BOOL_OP;OR;COMPOSITE_TEST;<Unused>;TEST @Value(vormcode) = 8'0.6'BOOL_OP;OR;COMPOSITE_TEST;<Unused>;TEST @Value(vormcode) = 9'0.6'BOOL_OP;OR;COMPOSITE_TEST;<Unused>;TEST @Value(vormcode) = 98'0.6'BOOL_OP;OR;COMPOSITE_TEST;<Unused>;TEST @Value(vormcode) = 99'0.6'FME_NUM_CONDITIONS10___
      SET_TO aantalknikken = FME_CONDITIONAL:DEFAULT_VALUE'0'BOOL_OP;OR;COMPOSITE_TEST;<Unused>;TEST @Value(soortkokervormigeconstructiecode) = 4'2'BOOL_OP;OR;COMPOSITE_TEST;<Unused>;TEST @Value(soortkokervormigeconstructiecode) = 5'2'FME_NUM_CONDITIONS3___
      SET_TO uittreeverlies = 1
      SET_TO administratiefgebiedcode = 17
    -> AttributeManager_6
AttributeManager_6
    ATTR_TABLE:
      SET_TO statusobjectcode = FME_CONDITIONAL:DEFAULT_VALUE'@Evaluate(@Value(statusobjectcode)/100)'BOOL_OP;OR;COMPOSITE_TEST;<Unused>;TEST @Value(statusobjectcode) = 9900'99'FME_NUM_CONDITIONS2___
      SET_TO indpeilregulpeilscheidend = FME_CONDITIONAL:DEFAULT_VALUE'_FME_NO_OP_'BOOL_OP;OR;COMPOSITE_TEST;<Unused>;TEST @Value(indpeilregulpeilscheidend) = j'1'BOOL_OP;OR;COMPOSITE_TEST;<Unused>;TEST @Value(indpeilregulpeilscheidend) = n'2'BOOL_OP;OR;COMPOSITE_TEST;<Unused>;TEST @Value(indpeilregulpeilscheidend) = o'3'BOOL_OP;OR;COMPOSITE_TEST;<Unused>;TEST indpeilregulpeilscheidend ATTRIBUTE_VALUE_NULL _FME_BLANK_STRING_'3'FME_NUM_CONDITIONS5___
      RENAME_SET_VALUE vormcode > vormkokercode
      REMOVE soortmateriaal
    -> NullAttributeMapper
NullAttributeMapper
    ATTRCHOICE = Selected Attributes
    ATTRLIST = statusobjectcode
    NEW_VALUE = 99
    NULL_TREATMENT = New Value
    OTHER_VALUE = 98
    SOURCE_ATTR_VAL = Null
    -> NullAttributeMapper_2
NullAttributeMapper_2
    ATTRCHOICE = Selected Attributes
    ATTRLIST = vormkokercode
    NEW_VALUE = 99
    NULL_TREATMENT = New Value
    OTHER_VALUE = 98
    SOURCE_ATTR_VAL = Null
    -> AnchoredSnapper_2 [CANDIDATE]

Bookmark: Dubbele duikers
Note: Kokers punten en lijnen samevoegen, om alle attributen mee te nemen voor punten
FeatureMerger_4 [off]
    ATTR_ACCUM_MODE = Merge Supplier
    ATTR_CONFLICT_RES = Use Requestor
    CLEANING_TOLERANCE = None
    IGNORE_NULLS = No
    JOIN_KEYS = @Value(WS_DUIKERSIFONHEVELCODE) @Value(CODE) AUTO
    MERGE_TYPE = Attributes Only
    PROCESS_DUPS = No
    REJECT_NULL_MISSING_KEYS = No
    SUPPLIERS_FIRST = No
    MERGED -> Tester_3 [off]
Note: Kokers met status 300 gaan door (in gebruik)
Tester_3 [off]
    BOOL_OP = OR
    TEST_CLAUSE = TEST @Value(STATUSOBJECT) = 300
    PASSED -> NeighborPairFinder_2 [BASE] [off]
    PASSED -> NeighborPairFinder_2 [CANDIDATE] [off]
Note: Kokers met met een koker binnen 4 m worden aan elkaar gematcht
NeighborPairFinder_2 [off]
    KEYATTR = WS_DUIKERSIFONHEVELCODE
    MAX = 4
    MINANGLE = 1
    MODE = Bases and Candidates
    MATCHED -> AttributeManager [off]
Note: Overbodige kolommen worden verwijderd en namen verduidelijkt
AttributeManager [off]
    ATTR_TABLE:
      SET_TO Code_base = @Value(WS_DUIKERSIFONHEVELCODE)
      SET_TO Richting_base = @Value(RICHTING)
      SET_TO Code_neighbour = @Value(_key2)
      SET_TO Distance_base_neighbour = @Value(_distance2)
      REMOVE WS_DUIKERSIFONHEVELCODE
      REMOVE OBJECTID
      REMOVE RICHTING
      REMOVE SE_ANNO_CAD_DATA
      REMOVE DUIKERSIFONHEVEL_ID_KOPIE
      REMOVE DUIKERSIFONHEVEL_ID
      REMOVE CODE
      REMOVE WS_NAAM
      REMOVE WS_OSMOMSCH
      REMOVE STATUSOBJECT
      REMOVE VORMKOKER
      REMOVE INDPEILREGULPEILSCHEIDEND
      REMOVE LENGTE
      REMOVE HOOGTEOPENING
      REMOVE BREEDTEOPENING
      REMOVE HOOGTEBOKBES
      REMOVE HOOGTEBOKBOS
      REMOVE SOORTMATERIAAL
      REMOVE SOORTKRUISING
      REMOVE HYPERLINK
      REMOVE WS_DOSSIERMAP
      REMOVE OPMERKING
      REMOVE WS_BEHEERDER
      REMOVE WS_GEW_ONDH
      REMOVE WS_BTNGEW_ONDH
      REMOVE OBJECTBEGINTIJD
      REMOVE OBJECTEINDTIJD
      REMOVE TIJDSTIPREGISTRATIE
      REMOVE EINDREGISTRATIE
      REMOVE NAAMSPACE
      REMOVE LOKAALID
      REMOVE LVPUBLICATIEDATUM
      REMOVE DETAILNIVEAUGEOMETRIE
      REMOVE DREMPELPEIL
      REMOVE SIGNALERINGSPEIL
      REMOVE SLUITPEIL
      REMOVE OPENKEERPEIL
      REMOVE OPENINGSPEIL
      REMOVE WATERKERINGID
      REMOVE WS_WATERKERINGCODE
      REMOVE WS_ONDERDEEL_CALAMITEITENPLAN
      REMOVE _heading1
      REMOVE _distance1
      REMOVE _key1
      REMOVE _heading2
      REMOVE _distance2
      REMOVE _key2
      REMOVE _candidate_angle1
      REMOVE _candidate_label_angle1
      REMOVE _candidate_angle2
      REMOVE _candidate_label_angle2
      REMOVE _closest_candidate_x1
      REMOVE _closest_candidate_y1
      REMOVE _closest_candidate_x2
      REMOVE _closest_candidate_y2
      REMOVE _closest_base_x1
      REMOVE _closest_base_x2
      REMOVE _closest_base_y1
      REMOVE _closest_base_y2
    -> FeatureMerger_5 [REQUESTOR] [off]
Note: Richting van de dubbele duiker wordt toegevoegd
FeatureMerger_5 [off]
    ATTR_ACCUM_MODE = Merge Supplier
    ATTR_CONFLICT_RES = Use Requestor
    CLEANING_TOLERANCE = None
    IGNORE_NULLS = No
    JOIN_KEYS = @Value(Code_neighbour) @Value(WS_DUIKERSIFONHEVELCODE) AUTO
    MERGE_TYPE = Attributes Only
    PROCESS_DUPS = No
    REJECT_NULL_MISSING_KEYS = No
    SUPPLIERS_FIRST = No
    MERGED -> AttributeManager_2 [off]
Note: Verschilhoek van duikers bepalen
AttributeManager_2 [off]
    ATTR_TABLE:
      SET_TO Richting_neighbour = @Value(RICHTING)
      SET_TO Hoek_verschil = @Evaluate(@Value(Richting_base)-@Value(Richting_neighbour))
      REMOVE WS_DUIKERSIFONHEVELCODE
      REMOVE RICHTING
      REMOVE SE_ANNO_CAD_DATA
      REMOVE DUIKERSIFONHEVEL_ID_KOPIE
      REMOVE DUIKERSIFONHEVEL_ID
    -> TestFilter [off]
Note: selectie van dubbele duikers met geloofwaardige verschilhoek
TestFilter [off]
    DEFAULT_VALUE = <UNFILTERED>
    TEST_LIST:
      BOOL_OP,AND,COMPOSITE_TEST,<Unused>,TEST_CLAUSE,"TEST @Value(Hoek_verschil) < 5
      TEST @Value(Hoek_verschil) > -5",Rondom5,BOOL_OP,AND,COMPOSITE_TEST,<Unused>,TEST_CLAUSE,"TEST @Value(Hoek_verschil) > -185
      TEST @Value(Hoek_verschil) < -175",Rondom-180,BOOL_OP,AND,COMPOSITE_TEST,<Unused>,TEST_CLAUSE,"TEST @Value(Hoek_verschil) < 185
      TEST @Value(Hoek_verschil) > 175",Rondom180
    Rondom5 -> SpatialFilter_2 [Candidate] [off]
    Rondom-180 -> SpatialFilter_2 [Candidate] [off]
    Rondom180 -> SpatialFilter_2 [Candidate] [off]
Note: Selectie van duikers welke op hydroobject vallen
SpatialFilter_2 [off]
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager_3 [off]
    FAILED -> AnchoredSnapper_3 [CANDIDATE] [off]
Note: 0,25 m snappen van watergang
AnchoredSnapper_3 [off]
    SNAPTYPE_PARAM = Segment Snapping
    TOLERANCE = 0.25
    SNAPPED -> AttributeManager_3 [off]
    UNTOUCHED -> AttributeManager_5 [off]
Note: liggen niet op watergang
Note: opschonen en aangeven of iets wel of niet op een lijn ligt
AttributeManager_5 [off]
    ATTR_TABLE:
      REMOVE OBJECTID
      REMOVE CODE
      REMOVE NAAM
      REMOVE STATUSOBJECT
      REMOVE SOORTOPPWATERKWANTITEIT
      REMOVE CATEGORIEOPPWATERLICHAAM
      REMOVE PERSISTENTIE
      REMOVE WS_OND_DROOG
      REMOVE WS_ONDH_NAT
      REMOVE WS_ONDH_BG
      REMOVE WS_ZANDSLOOT
      REMOVE DOSSIERMAP
      REMOVE IWS_W_WATPEIL
      REMOVE IWS_W_WATBRREFP
      REMOVE IWS_W_WATDIEPTE
      REMOVE IWS_W_INSTHGTEL
      REMOVE IWS_W_PLASBTALL
      REMOVE IWS_W_BRPLASBL
      REMOVE IWS_W_PLASBH_DL
      REMOVE IWS_W_TALUDL
      REMOVE IWS_W_BODBR
      REMOVE IWS_W_BODHO
      REMOVE WS_ONDERHOUDSMAAT
      REMOVE WS_ONDERHOUDSDIEPTE
      REMOVE IWS_W_TALUDR
      REMOVE IWS_W_PLASBH_DR
      REMOVE IWS_W_BRPLASBR
      REMOVE IWS_W_PLASBTALR
      REMOVE IWS_W_INSTHGTER
      REMOVE OBJECTBEGINTIJD
      REMOVE OBJECTEINDTIJD
      REMOVE TIJDSTIPREGISTRATIE
      REMOVE EINDREGISTRATIE
      REMOVE NAAMSPACE
      REMOVE LOKAALID
      REMOVE LVPUBLICATIEDATUM
      REMOVE DETAILNIVEAUGEOMETRIE
      REMOVE WS_ONDH_VAAR
      REMOVE WS_SCHOUW
      REMOVE WS_MODEL
      REMOVE OPMERKING
      REMOVE WS_MAAI
      REMOVE LENGTE
      REMOVE VISMIGRATIE
      REMOVE SE_ANNO_CAD_DATA
      REMOVE Richting_base
      REMOVE Richting_neighbour
      REMOVE Distance_base_neighbour
      REMOVE Hoek_verschil
      SET_TO Ligging = buiten lijn
    -> FeatureMerger_7 [SUPPLIER] [off]
Note: samenvoegen van duikers die op een lijnstuk liggen
Note: controle of de neighbour ook op een lijn ligt, door te kijken of deze ook in de base voorkomt, dan is er dus geen sprake van een 'dubbele duiker'
AttributeManager_3 [off]
    ATTR_TABLE:
      REMOVE OBJECTID
      REMOVE CODE
      REMOVE NAAM
      REMOVE STATUSOBJECT
      REMOVE SOORTOPPWATERKWANTITEIT
      REMOVE CATEGORIEOPPWATERLICHAAM
      REMOVE PERSISTENTIE
      REMOVE WS_OND_DROOG
      REMOVE WS_ONDH_NAT
      REMOVE WS_ONDH_BG
      REMOVE WS_ZANDSLOOT
      REMOVE DOSSIERMAP
      REMOVE IWS_W_WATPEIL
      REMOVE IWS_W_WATBRREFP
      REMOVE IWS_W_WATDIEPTE
      REMOVE IWS_W_INSTHGTEL
      REMOVE IWS_W_PLASBTALL
      REMOVE IWS_W_BRPLASBL
      REMOVE IWS_W_PLASBH_DL
      REMOVE IWS_W_TALUDL
      REMOVE IWS_W_BODBR
      REMOVE IWS_W_BODHO
      REMOVE WS_ONDERHOUDSMAAT
      REMOVE WS_ONDERHOUDSDIEPTE
      REMOVE IWS_W_TALUDR
      REMOVE IWS_W_PLASBH_DR
      REMOVE IWS_W_BRPLASBR
      REMOVE IWS_W_PLASBTALR
      REMOVE IWS_W_INSTHGTER
      REMOVE OBJECTBEGINTIJD
      REMOVE OBJECTEINDTIJD
      REMOVE TIJDSTIPREGISTRATIE
      REMOVE EINDREGISTRATIE
      REMOVE NAAMSPACE
      REMOVE LOKAALID
      REMOVE LVPUBLICATIEDATUM
      REMOVE DETAILNIVEAUGEOMETRIE
      REMOVE WS_ONDH_VAAR
      REMOVE WS_SCHOUW
      REMOVE WS_MODEL
      REMOVE OPMERKING
      REMOVE WS_MAAI
      REMOVE LENGTE
      REMOVE VISMIGRATIE
      REMOVE SE_ANNO_CAD_DATA
      REMOVE Richting_base
      REMOVE Richting_neighbour
      REMOVE Distance_base_neighbour
      REMOVE Hoek_verschil
      REMOVE _predicate
    -> FeatureMerger_6 [REQUESTOR] [off]
    -> FeatureMerger_6 [SUPPLIER] [off]
FeatureMerger_6 [off]
    ATTR_ACCUM_MODE = Merge Supplier
    ATTR_CONFLICT_RES = Use Requestor
    CLEANING_TOLERANCE = None
    IGNORE_NULLS = No
    JOIN_KEYS = @Value(Code_neighbour) @Value(Code_base) AUTO
    MERGE_TYPE = Attributes Only
    PROCESS_DUPS = No
    REJECT_NULL_MISSING_KEYS = No
    SUPPLIERS_FIRST = No
    UNMERGED_REQUESTOR -> AttributeManager_4 [off]
Note: liggen wel op watergang
AttributeManager_4 [off]
    ATTR_TABLE = SET_TO Ligging = Lijn
    -> FeatureMerger_7 [REQUESTOR] [off]
Note: dubbelen er uit halen met A hoort bij B en B hoort bij A
FeatureMerger_7 [off]
    ATTR_ACCUM_MODE = Merge Supplier
    ATTR_CONFLICT_RES = Use Requestor
    CLEANING_TOLERANCE = None
    IGNORE_NULLS = No
    JOIN_KEYS = @Value(Code_neighbour) @Value(Code_base) AUTO
    MERGE_TYPE = Attributes Only
    PROCESS_DUPS = No
    REJECT_NULL_MISSING_KEYS = No
    SUPPLIERS_FIRST = No
    MERGED -> FeatureMerger_7_Merged [off]
    UNUSED_SUPPLIER -> FeatureMerger_7_UnusedSupplier [off]
Note: Dubbele duikers, met hoofdduiker (liggend op hydroobject als base)
FeatureMerger_7_Merged: Inspector [off]
Note: Naar alle waarschijnlijkheid zijn dit de driedubbele duikers die niet zijn gematcht
FeatureMerger_7_UnusedSupplier: Inspector [off]

Bookmark: Duikers snappen op watergang
Note: Snap op watergang, / tolerance 0,25m
