FME workspace HDSR_Hydamo_DwarsProfiel.fmw

Parameters:
- SourceDataset_ESRISHAPE = $(FME_MF_DIR)profielen\HDSR_2012_met_geprojecteerd_3d_shape.shp   # Source Esri Shapefile(s)
- DestDataset_GML2 = $(FME_MF_DIR)output\dwarsprofiel.gml   # Destination Geography Markup Language (GML) v2.1.2 File

Readers:
- ESRISHAPE_1: ESRISHAPE from $(SourceDataset_ESRISHAPE)

Writers:
- GML2_1: GML2 to $(DestDataset_GML2) in EPSG:28992

HDSR_2012_met_geprojecteerd_3d_shape (reader ESRISHAPE_1)
    attributes: X double, Y double, Z double, PROFILEID char(254), POINTORDER double, POINTCATEG double
    -> Tester
    -> AttributeManager
Tester [off]
    BOOL_OP = OR
    TEST_CLAUSE = TEST @Value(POINTCATEG) = 99
    PASSED -> AttributeManager
AttributeManager
    ATTR_TABLE:
      SET_TO code = @Value(PROFILEID)_@Value(POINTORDER)
      SET_TO statusobjectcode = 3
      SET_TO objectbegintijd
      SET_TO objecteindtijd
      RENAME_SET_VALUE POINTORDER > codevolgnummer
      RENAME_SET_VALUE PROFILEID > profielcode
      SET_TO typeprofielcode = 4
      SET_TO ruwheidstypecode = 4
      SET_TO ruwheidswaardelaag = 35
      SET_TO ruwheidswaardehoog = 25
      SET_TO administratiefgebiedcode = 17
      REMOVE X
      REMOVE Y
      REMOVE Z
      REMOVE POINTCATEG
    -> dwarsprofiel (writer GML2_1)
    -> AttributeManager_Output
AttributeManager_Output: Inspector

Bookmark: GML writer
dwarsprofiel (writer GML2_1)
    attributes: code xml_char(200), statusobjectcode xml_char(200), objectbegintijd xml_char(200), objecteindtijd xml_char(200), codevolgnummer xml_char(200), profielcode xml_char(200), typeprofielcode xml_char(200), ruwheidstypecode xml_char(200), ruwheidswaardelaag xml_char(200), ruwheidswaardehoog xml_char(200), administratiefgebiedcode xml_char(200)
