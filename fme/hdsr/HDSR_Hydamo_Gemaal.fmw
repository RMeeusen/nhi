FME workspace HDSR_Hydamo_Gemaal.fmw

Parameters:
- SourceDataset_ORACLE_SPATIAL = Raadpleger_IRISPRD   # Connection
- SourceDataset_ORACLE_SPATIAL_5 = Raadpleger_IRISPRD   # Connection
- DestDataset_GML2 = $(FME_MF_DIR)output\gemaal.gml   # Destination Geography Markup Language (GML) v2.1.2 File
- DestDataset_GML2_5 = $(FME_MF_DIR)output\pomp.gml   # Destination Geography Markup Language (GML) v2.1.2 File
- DestDataset_GML2_4 = $(FME_MF_DIR)output\sturing_gemaal.gml   # Destination Geography Markup Language (GML) v2.1.2 File

Readers:
- ORACLE_SPATIAL_1: ORACLE_SPATIAL from $(SourceDataset_ORACLE_SPATIAL)
- ORACLE_SPATIAL_2: ORACLE_SPATIAL from $(SourceDataset_ORACLE_SPATIAL_5)

Writers:
- GML2_1: GML2 to $(DestDataset_GML2) in EPSG:28992
- GML2_2: GML2 to $(DestDataset_GML2_5) in EPSG:28992
- GML2_3: GML2 to $(DestDataset_GML2_4)

HYDROOBJECT (reader ORACLE_SPATIAL_1)
    attributes: OBJECTID number(38,0), CODE varchar2(50), NAAM varchar2(250), STATUSOBJECT number(5,0), SOORTOPPWATERKWANTITEIT number(5,0), CATEGORIEOPPWATERLICHAAM number(5,0), PERSISTENTIE number(5,0), WS_OND_DROOG number(5,0), WS_ONDH_NAT number(5,0), WS_ONDH_BG number(5,0), WS_ZANDSLOOT varchar2(1), DOSSIERMAP varchar2(15), IWS_W_WATPEIL number(38,8), IWS_W_WATBRREFP number(38,8), IWS_W_WATDIEPTE number(38,8), IWS_W_INSTHGTEL number(38,8), IWS_W_PLASBTALL number(38,8), IWS_W_BRPLASBL number(38,8), IWS_W_PLASBH_DL number(38,8), IWS_W_TALUDL number(38,8), IWS_W_BODBR number(38,8), IWS_W_BODHO number(38,8), WS_ONDERHOUDSMAAT number(38,8), WS_ONDERHOUDSDIEPTE number(38,8), IWS_W_TALUDR number(38,8), IWS_W_PLASBH_DR number(38,8), IWS_W_BRPLASBR number(38,8), IWS_W_PLASBTALR number(38,8), IWS_W_INSTHGTER number(38,8), OBJECTBEGINTIJD date,
      OBJECTEINDTIJD date, TIJDSTIPREGISTRATIE date, EINDREGISTRATIE date, NAAMSPACE varchar2(50), LOKAALID varchar2(50), LVPUBLICATIEDATUM date, DETAILNIVEAUGEOMETRIE number(38,8), WS_ONDH_VAAR varchar2(1), WS_SCHOUW varchar2(1), WS_MODEL varchar2(1), OPMERKING varchar2(500), WS_MAAI varchar2(1), LENGTE number(38,8), VISMIGRATIE varchar2(1), SE_ANNO_CAD_DATA blob
    -> AnchoredSnapper [ANCHOR]
GEMAAL (reader ORACLE_SPATIAL_2)
    attributes: GEMAALID number(38,0), CODE varchar2(50), NAAM varchar2(50), WS_CAWNR varchar2(50), WS_OSMOMSCH varchar2(60), STATUSOBJECT number(5,0), WS_GMLSOORT number(5,0), WS_GMLFUNCTIE number(5,0), WS_AANTALPOMPEN number(5,0), MAXIMALECAPACITEIT number(38,8), HYPERLINK varchar2(500), WS_DOSSIERMAP varchar2(15), OPMERKING varchar2(500), WS_BEHEERDER number(5,0), WS_AFST_BED varchar2(1), WS_AFSLUITWIJZE_KERING number(5,0), WS_ONDERDEEL_CALAMITEITENPLAN varchar2(1), WS_ONDERDEELWATERKERING varchar2(1), RICHTING number(38,8), OBJECTBEGINTIJD date, OBJECTEINDTIJD date, TIJDSTIPREGISTRATIE date, EINDREGISTRATIE date, NAAMSPACE varchar2(50), LOKAALID varchar2(50), LVPUBLICATIEDATUM date, DETAILNIVEAUGEOMETRIE number(38,8), SE_ANNO_CAD_DATA blob, WS_GEW_ONDH number(5,0), WS_BTNGEW_ONDH number(5,0)
    -> AttributeManager
AttributeManager
    ATTR_TABLE:
      REMOVE GEMAALID
      RENAME_SET_VALUE CODE > code
      RENAME_SET_VALUE NAAM > naam
      REMOVE WS_CAWNR
      REMOVE WS_OSMOMSCH
      RENAME_SET_VALUE STATUSOBJECT > statusobjectcode = FME_CONDITIONAL:DEFAULT_VALUE'@Evaluate(@Value(statusobjectcode)/100)'BOOL_OP;OR;COMPOSITE_TEST;<Unused>;TEST @Value(statusobjectcode) = 9900'98'FME_NUM_CONDITIONS2___
      REMOVE WS_GMLSOORT
      RENAME_SET_VALUE HYPERLINK > hyperlink
      REMOVE WS_DOSSIERMAP
      REMOVE OPMERKING
      REMOVE WS_BEHEERDER
      REMOVE WS_AFST_BED
      REMOVE WS_AFSLUITWIJZE_KERING
      REMOVE WS_ONDERDEEL_CALAMITEITENPLAN
      REMOVE WS_ONDERDEELWATERKERING
      REMOVE RICHTING
      RENAME_SET_VALUE OBJECTBEGINTIJD > objectbegintijd
      RENAME_SET_VALUE OBJECTEINDTIJD > objecteindtijd
      REMOVE TIJDSTIPREGISTRATIE
      REMOVE EINDREGISTRATIE
      REMOVE NAAMSPACE
      REMOVE LOKAALID
      REMOVE LVPUBLICATIEDATUM
      REMOVE DETAILNIVEAUGEOMETRIE
      REMOVE SE_ANNO_CAD_DATA
      REMOVE WS_GEW_ONDH
      REMOVE WS_BTNGEW_ONDH
      SET_TO administratiefgebiedcode = 17
    -> AnchoredSnapper [CANDIDATE]
AnchoredSnapper
    EXTEND_LINES = NEVER
    SNAPTYPE_PARAM = End Point Snapping
    TOLERANCE = 0.1
    SNAPPED -> Cloner
    SNAPPED -> AttributeManager_5
    UNTOUCHED -> Cloner
    UNTOUCHED -> AttributeManager_5
AttributeManager_10_Output: Inspector
pomp (writer GML2_2)
    attributes: code xml_char(200), codegerelateerdobject xml_char(200), statusobjectcode xml_char(200), objectbegintijd xml_char(200), objecteindtijd xml_char(200), maximalecapaciteit xml_char(200), pompcurve xml_char(200), administratiefgebiedcode xml_char(200)
AttributeManager_5
    ATTR_TABLE:
      REMOVE WS_AANTALPOMPEN
      REMOVE MAXIMALECAPACITEIT
      REMOVE WS_GMLFUNCTIE
    -> AttributeManager_5_Output
    -> gemaal (writer GML2_1)
AttributeManager_5_Output: Inspector
gemaal (writer GML2_1)
    attributes: code xml_char(200), naam xml_char(200), statusobjectcode xml_char(200), objectbegintijd xml_char(200), objecteindtijd xml_char(200), hyperlink xml_char(200), administratiefgebiedcode xml_char(200)

Bookmark: Pompen aanmaken
Cloner
    COPIES = @Value(WS_AANTALPOMPEN)
    COPYATT = _copynum
    COPY -> AttributeManager_2
    <REJECTED> -> AttributeManager_2
AttributeManager_2
    ATTR_TABLE:
      RENAME_SET_VALUE MAXIMALECAPACITEIT > maximalecapaciteit
      REMOVE fme_rejection_code
      SET_TO codegerelateerdobject = @Value(code)
      SET_TO pompcurve
      SET_TO _copynum+1 = @add(@Value(_copynum),1,...)
    -> AttributeManager_3
Note: Aanname: capaciteit per pomp = totale capaciteit / aantal pompen
AttributeManager_3
    ATTR_TABLE:
      SET_TO code = @Value(code)_@Value(_copynum+1)
      SET_TO maximalecapaciteit = @div(@Value(maximalecapaciteit),@Value(WS_AANTALPOMPEN))
    -> AttributeManager_4
AttributeManager_4
    ATTR_TABLE:
      REMOVE hyperlink
      REMOVE _copynum
      REMOVE _copynum+1
      REMOVE WS_AANTALPOMPEN
    -> AttributeManager_6
    -> AttributeManager_10
AttributeManager_10
    ATTR_TABLE:
      REMOVE naam
      REMOVE WS_GMLFUNCTIE
    -> pomp (writer GML2_2)
    -> AttributeManager_10_Output

Bookmark: Sturing toevoegen
AttributeManager_6
    ATTR_TABLE:
      SET_TO code = sturing_@Value(code)
      SET_TO codegerelateerdobject = @Right(@Value(code),7)
      REMOVE maximalecapaciteit
      REMOVE pompcurve
      SET_TO complexesturingcode = n
      SET_TO hyperlink
      SET_TO geldigbegintijd
      SET_TO geldigeindtijd
      SET_TO stuurvariabelecode = 3
      SET_TO doelvariabelecode = 1
      SET_TO streefwaarde
      SET_TO bovenmarge
      SET_TO ondermarge
      SET_TO sturingtypecode = discreet
      SET_TO gemaal = @Left(@Value(codegerelateerdobject),5)
    -> TestFilter
TestFilter
    DEFAULT_VALUE = <UNFILTERED>
    TEST_LIST:
      BOOL_OP,OR,COMPOSITE_TEST,<Unused>,TEST_CLAUSE,"TEST @Value(WS_GMLFUNCTIE) = 1
      TEST @Value(WS_GMLFUNCTIE) = 3",bovenpeil,BOOL_OP,OR,COMPOSITE_TEST,<Unused>,TEST_CLAUSE,"TEST @Value(WS_GMLFUNCTIE) = 2
      TEST @Value(WS_GMLFUNCTIE) = 4",benedenpeil
    bovenpeil -> DatabaseJoiner_2
    benedenpeil -> DatabaseJoiner
Note: Streefpeilen uit CAW export, marges zelf bedacht
DatabaseJoiner_2
    ADDED_FIELDS = TagOmschrijving Waarde
    ATTR_ACCUM_MODE = Merge Joined
    ATTR_CONFLICT_RES = Use Original
    CSV2_CASE_SENSITIVE_FIELD_NAMES = Yes
    CSV2_DATA_START_LINE = 2
    CSV2_DELIMITER = ;
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_READ_SKIPPED_LINES = No
    CSV2_SCAN_ADDITIONAL_FIELDS = No
    CSV2_SCAN_MAX_ROWS = 1000
    CSV2_SCAN_TYPES = No
    CSV2_SCHEMA = LocId,string,NO;LocOmschrijving,string,YES;AppGroepId,string,NO;AppGroepOmschrijving,string,NO;InfoBlokType,string,NO;InfoblokOmschrijving,string,NO;IBvolgnr,string,NO;TagId,string,NO;TagOmschrijving,string,YES;Adres,string,NO;GegType,string,NO;GegTypeAfkorting,string,NO;MinGebruiker,string,NO;MaxGebruiker,string,NO;Eenheid,string,NO;Waarde,string,YES;Kwaliteit,string,NO;Tijdstip,string,NO
    CSV2_SKIP_DUPLICATE_DELIMITERS = No
    CSV2_TRIM_FIELD_NAME_QUALIFIERS = Yes
    CSV2_TRIM_FIELD_VALUE_QUALIFIERS = Yes
    CSV2_USE_CUSTOM_SCHEMA = YES
    DATASET = H:\DATA\Service\EPKE\TKI D-Hydro\20171002_AllIeInstellingen.csv
    FORMAT = CSV2
    JOIN_KEYS = naam LocOmschrijving
    MATCH_MULTIPLE_DISPLAY = Create a feature for each match
    MATCH_RULE_DISPLAY = Match All (1:M)
    TABLE = CSV
    JOINED -> Tester_2
Tester_2
    BOOL_OP = OR
    TEST_CLAUSE:
      TEST @Value(TagOmschrijving) = Streefpeil
      TEST @Value(TagOmschrijving) CONTAINS Streefbovenpeil
    PASSED -> AttributeManager_12
AttributeManager_12
    ATTR_TABLE:
      SET_TO streefwaarde = @Value(Waarde)
      SET_TO bovenmarge = FME_CONDITIONAL:DEFAULT_VALUE'_FME_NO_OP_'BOOL_OP;OR;COMPOSITE_TEST;<Unused>;TEST @Value(code) ENDS_WITH 1'0'BOOL_OP;OR;COMPOSITE_TEST;<Unused>;TEST @Value(code) ENDS_WITH 2'-0.02'FME_NUM_CONDITIONS3___
      SET_TO ondermarge = FME_CONDITIONAL:DEFAULT_VALUE'_FME_NO_OP_'BOOL_OP;OR;COMPOSITE_TEST;<Unused>;TEST @Value(code) ENDS_WITH 1'-0.03'BOOL_OP;OR;COMPOSITE_TEST;<Unused>;TEST @Value(code) ENDS_WITH 2'-0.05'FME_NUM_CONDITIONS3___
      REMOVE gemaal
      REMOVE naam
      REMOVE WS_GMLFUNCTIE
      REMOVE TagOmschrijving
      REMOVE Waarde
      REMOVE _matched_records
    -> AttributeManager_7
Note: Streefpeilen uit CAW export, marges o.b.v. De Tol
DatabaseJoiner
    ADDED_FIELDS = TagOmschrijving Waarde
    ATTR_ACCUM_MODE = Merge Joined
    ATTR_CONFLICT_RES = Use Original
    CSV2_CASE_SENSITIVE_FIELD_NAMES = Yes
    CSV2_DATA_START_LINE = 2
    CSV2_DELIMITER = ;
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_READ_SKIPPED_LINES = No
    CSV2_SCAN_ADDITIONAL_FIELDS = No
    CSV2_SCAN_MAX_ROWS = 1000
    CSV2_SCAN_TYPES = No
    CSV2_SCHEMA = LocId,string,NO;LocOmschrijving,string,YES;AppGroepId,string,NO;AppGroepOmschrijving,string,NO;InfoBlokType,string,NO;InfoblokOmschrijving,string,NO;IBvolgnr,string,NO;TagId,string,NO;TagOmschrijving,string,YES;Adres,string,NO;GegType,string,NO;GegTypeAfkorting,string,NO;MinGebruiker,string,NO;MaxGebruiker,string,NO;Eenheid,string,NO;Waarde,string,YES;Kwaliteit,string,NO;Tijdstip,string,NO
    CSV2_SKIP_DUPLICATE_DELIMITERS = No
    CSV2_TRIM_FIELD_NAME_QUALIFIERS = Yes
    CSV2_TRIM_FIELD_VALUE_QUALIFIERS = Yes
    CSV2_USE_CUSTOM_SCHEMA = YES
    DATASET = H:\DATA\Service\EPKE\TKI D-Hydro\20171002_AllIeInstellingen.csv
    FORMAT = CSV2
    JOIN_KEYS = naam LocOmschrijving
    MATCH_MULTIPLE_DISPLAY = Create a feature for each match
    MATCH_RULE_DISPLAY = Match All (1:M)
    TABLE = CSV
    JOINED -> Tester
Tester
    BOOL_OP = OR
    TEST_CLAUSE:
      TEST @Value(TagOmschrijving) = Streefpeil
      TEST @Value(TagOmschrijving) CONTAINS Streefbenedenpeil
    PASSED -> AttributeManager_11
AttributeManager_11
    ATTR_TABLE:
      SET_TO streefwaarde = @Value(Waarde)
      SET_TO bovenmarge = FME_CONDITIONAL:DEFAULT_VALUE'_FME_NO_OP_'BOOL_OP;OR;COMPOSITE_TEST;<Unused>;TEST @Value(code) ENDS_WITH 1'0.02'BOOL_OP;OR;COMPOSITE_TEST;<Unused>;TEST @Value(code) ENDS_WITH 2'0.04'FME_NUM_CONDITIONS3___
      SET_TO ondermarge = FME_CONDITIONAL:DEFAULT_VALUE'_FME_NO_OP_'BOOL_OP;OR;COMPOSITE_TEST;<Unused>;TEST @Value(code) ENDS_WITH 1'-0.06'BOOL_OP;OR;COMPOSITE_TEST;<Unused>;TEST @Value(code) ENDS_WITH 2'-0.03'FME_NUM_CONDITIONS3___
      REMOVE gemaal
      REMOVE naam
      REMOVE WS_GMLFUNCTIE
      REMOVE TagOmschrijving
      REMOVE Waarde
      REMOVE _matched_records
    -> AttributeManager_7
AttributeManager_7
    ATTR_TABLE = REMOVE administratiefgebiedcode
    -> AttributeManager_7_Output
    -> sturing_gemaal (writer GML2_3)
AttributeManager_7_Output: Inspector
sturing_gemaal (writer GML2_3)
    attributes: code xml_char(200), codegerelateerdobject xml_char(200), statusobjectcode xml_char(200), objectbegintijd xml_char(200), objecteindtijd xml_char(200), complexesturingcode xml_char(200), hyperlink xml_char(200), geldigbegintijd xml_char(200), geldigeindtijd xml_char(200), stuurvariabelecode xml_char(200), doelvariabelecode xml_char(200), streefwaarde xml_char(200), bovenmarge xml_char(200), ondermarge xml_char(200), sturingtypecode xml_char(200)
