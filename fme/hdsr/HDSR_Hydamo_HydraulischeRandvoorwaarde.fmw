FME workspace HDSR_Hydamo_HydraulischeRandvoorwaarde.fmw

Parameters:
- DestDataset_ESRISHAPE = H:\DATA\Service\Jantine\Sobek\Catchment en Channel Builder\Nieuwbouw_channelbuilder_2018\Boundaries   # Destination Esri Shapefile Folder
- DestDataset_GML2 = $(FME_MF_DIR)output\hydraulischerandvoorwaarde.gml   # Destination Geography Markup Language (GML) v2.1.2 File
- SourceDataset_ESRISHAPE_6 = H:\DATA\Service\Jantine\Sobek\Catchment en Channel Builder\Nieuwbouw_channelbuilder_2018\Boundaries\HydraulischeRondvoorwaarden_aanpassing_mei2019.shp   # Source Esri Shapefile(s)

Readers:
- ESRISHAPE_1: ESRISHAPE from $(SourceDataset_ESRISHAPE_6)

Writers:
- ESRISHAPE_2: ESRISHAPE to $(DestDataset_ESRISHAPE)
- GML2_1: GML2 to $(DestDataset_GML2) in EPSG:28992

HydraulischeRondvoorwaarden_aanpassing_mei2019 (reader ESRISHAPE_1)
    attributes: code char(200), waterstand char(200), administra char(200), statusobje char(200), Watergang char(50), BOUNDTYPE char(20)
    -> Counter
    -> HydraulischeRondvoorwaarden_aanpassing_mei2019
Counter
    CNT_ATTR = _count
    DOMAIN = counter
    SCOPE = Local
    START = 1
    -> AttributeCreator
AttributeCreator
    ATTR_TABLE:
      SET_TO code = HR_@Value(_count)
      SET_TO typerandvoorwaardecode = FME_CONDITIONAL:DEFAULT_VALUE'_FME_NO_OP_'BOOL_OP;OR;COMPOSITE_TEST;<Unused>;TEST @Value(BOUNDTYPE) = H'0'FME_NUM_CONDITIONS2___
      SET_TO administratiefgebiedcode = FME_CONDITIONAL:DEFAULT_VALUE'_FME_NO_OP_'BOOL_OP;OR;COMPOSITE_TEST;<Unused>;TEST @Value(Watergang) = ARK;TEST @Value(Watergang) = Lek;TEST @Value(Watergang) = Hollandse IJssel'0'BOOL_OP;OR;COMPOSITE_TEST;<Unused>;TEST @Value(Watergang) = de Geer;TEST @Value(Watergang) = Vecht'2'BOOL_OP;OR;COMPOSITE_TEST;<Unused>;TEST @Value(Watergang) = De Meije;TEST @Value(Watergang) = Oude Rijn'13'FME_NUM_CONDITIONS4___
      SET_TO statusobjectcode = 300
    -> AttributeRemover
AttributeRemover
    REMOVE_ATTRS = Waarde,Id,In_of_uit,Type
    -> AttributeManager
AttributeManager
    ATTR_TABLE:
      SET_TO statusobjectcode = FME_CONDITIONAL:DEFAULT_VALUE'@Evaluate(@Value(statusobjectcode)/100)'BOOL_OP;OR;COMPOSITE_TEST;<Unused>;TEST @Value(statusobjectcode) = 9900'98'FME_NUM_CONDITIONS2___
      SET_TO objectbegintijd
      SET_TO objecteindtijd
      SET_TO debiet
      REMOVE Watergang
      SET_TO qhrelatie
      REMOVE _count
      REMOVE administra
      REMOVE statusobje
      REMOVE BOUNDTYPE
    -> HydraulischeRandvoorwaarde (writer ESRISHAPE_2)
    -> hydraulischerandvoorwaarde (writer GML2_1)
    -> AttributeManager_Output
AttributeManager_Output: Inspector
HydraulischeRandvoorwaarde (writer ESRISHAPE_2) [off]
    attributes: code char(200), statusobje char(200), objectbegi char(200), objecteind char(200), typerandvo char(200), waterstand char(200), debiet char(200), qhrelatie char(200), administra char(200)
hydraulischerandvoorwaarde (writer GML2_1)
    attributes: code xml_char(200), statusobjectcode xml_char(200), objectbegintijd xml_char(200), objecteindtijd xml_char(200), typerandvoorwaardecode xml_char(200), waterstand xml_char(200), debiet xml_char(200), qhrelatie xml_char(200), administratiefgebiedcode xml_char(200)
HydraulischeRondvoorwaarden_aanpassing_mei2019: Inspector
