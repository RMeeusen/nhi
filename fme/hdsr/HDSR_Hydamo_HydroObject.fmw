FME workspace HDSR_Hydamo_HydroObject.fmw

Parameters:
- SourceDataset_ORACLE_SPATIAL_3 = Raadpleger_IRISPRD   # Connection
- DestDataset_GML2 = $(FME_MF_DIR)output\hydroobject.gml   # Destination Geography Markup Language (GML) v2.1.2 File

Readers:
- ORACLE_SPATIAL_1: ORACLE_SPATIAL from $(SourceDataset_ORACLE_SPATIAL_3)

Writers:
- GML2_1: GML2 to $(DestDataset_GML2) in EPSG:28992

Note: HDSR-deel: Inger de Groot:11-10-2018
Note: In DAMO liggen al verschillende knips in de watergangen (samenkomst, duiker, sifon). Dit in tegenstelling tot de oude database. Voor ons zijn de knips t.h.v. de sifons niet gewenst, hier moeten de watergangen geplakt worden. / Moet dat hier ook?
ArcSDEGridSnapper
    OUTPUT_INT = No
    PRECISION_DISPLAY = High precision (53 bit)
    SCALE = 100
    XMIN = 0
    YMIN = 0
    ZMIN = 0
    ZSCALE = 1
    SNAPPED -> Tester
Tester
    BOOL_OP = OR
    TEST_CLAUSE = TEST @Value(CATEGORIEOPPWATERLICHAAM) NOT_= 99
    PASSED -> AttributeKeeper_3
AttributeManager_Output: Inspector

Bookmark: HDSR
  Inlezen hydro-objecten met status gerealiseerd/in bedrijf/... (statusobject =300) 
  Eventueel álle objecten inlezen (dus ook planvorming, dan codes netjes omzetten naar 1,2,3,4 volgens hydamo)
HYDROOBJECT (reader ORACLE_SPATIAL_1)
    attributes: OBJECTID number(38,0), CODE varchar2(50), NAAM varchar2(250), STATUSOBJECT number(5,0), SOORTOPPWATERKWANTITEIT number(5,0), CATEGORIEOPPWATERLICHAAM number(5,0), PERSISTENTIE number(5,0), WS_OND_DROOG number(5,0), WS_ONDH_NAT number(5,0), WS_ONDH_BG number(5,0), WS_ZANDSLOOT varchar2(1), DOSSIERMAP varchar2(15), IWS_W_WATPEIL number(38,8), IWS_W_WATBRREFP number(38,8), IWS_W_WATDIEPTE number(38,8), IWS_W_INSTHGTEL number(38,8), IWS_W_PLASBTALL number(38,8), IWS_W_BRPLASBL number(38,8), IWS_W_PLASBH_DL number(38,8), IWS_W_TALUDL number(38,8), IWS_W_BODBR number(38,8), IWS_W_BODHO number(38,8), WS_ONDERHOUDSMAAT number(38,8), WS_ONDERHOUDSDIEPTE number(38,8), IWS_W_TALUDR number(38,8), IWS_W_PLASBH_DR number(38,8), IWS_W_BRPLASBR number(38,8), IWS_W_PLASBTALR number(38,8), IWS_W_INSTHGTER number(38,8), OBJECTBEGINTIJD date,
      OBJECTEINDTIJD date, TIJDSTIPREGISTRATIE date, EINDREGISTRATIE date, NAAMSPACE varchar2(50), LOKAALID varchar2(50), LVPUBLICATIEDATUM date, DETAILNIVEAUGEOMETRIE number(38,8), WS_ONDH_VAAR varchar2(1), WS_SCHOUW varchar2(1), WS_MODEL varchar2(1), OPMERKING varchar2(500), WS_MAAI varchar2(1), LENGTE number(38,8), VISMIGRATIE varchar2(1), SE_ANNO_CAD_DATA blob
    -> ArcSDEGridSnapper

Bookmark: aanmaken velden Hydamo en vullen
  LET op! Hier worden aannames voor ruwheid gedaan.
AttributeKeeper_3
    KEEP_ATTRS = OBJECTEINDTIJD,STATUSOBJECT,OBJECTBEGINTIJD,NAAM,CATEGORIEOPPWATERLICHAAM,CODE
    -> AttributeRenamer_3
AttributeRenamer_3
    ATTR_TABLE:
      RENAME_SET_DEFAULT CODE > code
      RENAME_SET_DEFAULT NAAM > naam
      RENAME_SET_DEFAULT STATUSOBJECT > statusobjectcode
      RENAME_SET_DEFAULT OBJECTBEGINTIJD > objectbegintijd
      RENAME_SET_DEFAULT OBJECTEINDTIJD > objecteindtijd
    -> AttributeCreator_7
Note: aaannames voor ruwheid. / Laag: winter (35/30) / Hoog : zomer (25/15)
AttributeCreator_7
    ATTR_TABLE:
      SET_TO hyperlink
      SET_TO ruwheidstypecode = 4
      SET_TO ruwheidswaardelaag = FME_CONDITIONAL:DEFAULT_VALUE'30'BOOL_OP;OR;COMPOSITE_TEST;<Unused>;TEST @Value(CATEGORIEOPPWATERLICHAAM) = 1'35'FME_NUM_CONDITIONS2___
      SET_TO ruwheidswaardehoog = FME_CONDITIONAL:DEFAULT_VALUE'15'BOOL_OP;OR;COMPOSITE_TEST;<Unused>;TEST @Value(CATEGORIEOPPWATERLICHAAM) = 1'25'FME_NUM_CONDITIONS2___
      SET_TO administratiefgebiedcode = 17
    -> AttributeManager
AttributeManager
    ATTR_TABLE:
      SET_TO statusobjectcode = FME_CONDITIONAL:DEFAULT_VALUE'@Evaluate(@Value(statusobjectcode)/100)'BOOL_OP;OR;COMPOSITE_TEST;<Unused>;TEST @Value(statusobjectcode) = 9900'98'FME_NUM_CONDITIONS2___
      REMOVE CATEGORIEOPPWATERLICHAAM
    -> hydroobject (writer GML2_1)
    -> AttributeManager_Output

Bookmark: output gecontroleerd tegen xsd schema
hydroobject (writer GML2_1)
    attributes: code xml_char(200), naam xml_char(200), statusobjectcode xml_char(200), objectbegintijd xml_char(200), objecteindtijd xml_char(200), hyperlink xml_char(200), ruwheidstypecode xml_char(200), ruwheidswaardelaag xml_char(200), ruwheidswaardehoog xml_char(200), administratiefgebiedcode xml_char(200)
