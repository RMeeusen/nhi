FME workspace HDSR_HyDAMO_NormGeparametriseerdProfiel.fmw

Parameters:
- SourceDataset_ORACLE_SPATIAL_3 = Raadpleger_IRISPRD   # Connection
- DestDataset_GML2 = $(FME_MF_DIR)output\normgeparametriseerdprofiel.gml   # Destination Geography Markup Language (GML) v2.1.2 File

Readers:
- ORACLE_SPATIAL_1: ORACLE_SPATIAL from $(SourceDataset_ORACLE_SPATIAL_3)

Writers:
- GML2_1: GML2 to $(DestDataset_GML2) in EPSG:28992

Note: Wijzigingen: / 06-02-2017 Esther Aanpassing om in te haken op DAMO-W. / HDSR-deel: Inger de Groot: 19-6-2018 / Aangepast voor Norm Geparametriseerde Profielen: 10-4-2019 Jantine Hoekstra / Aanpassingen o.b.v. HyDamao Datamodel: 20-8-2019 Epke van der Werf
ArcSDEGridSnapper
    OUTPUT_INT = No
    PRECISION_DISPLAY = High precision (53 bit)
    SCALE = 100
    XMIN = 0
    YMIN = 0
    ZMIN = 0
    ZSCALE = 1
    SNAPPED -> AttributeKeeper_3
AttributeCreator_7_Output: Inspector

Bookmark: HDSR
  Inlezen hydro-objecten met status gerealiseerd/in bedrijf/... (statusobject =300) 
  Eventueel álle objecten inlezen (dus ook planvorming, dan codes netjes omzetten naar 1,2,3,4 volgens hydamo)
HYDROOBJECT (reader ORACLE_SPATIAL_1)
    attributes: OBJECTID number(38,0), CODE varchar2(50), NAAM varchar2(250), STATUSOBJECT number(5,0), SOORTOPPWATERKWANTITEIT number(5,0), CATEGORIEOPPWATERLICHAAM number(5,0), PERSISTENTIE number(5,0), WS_OND_DROOG number(5,0), WS_ONDH_NAT number(5,0), WS_ONDH_BG number(5,0), WS_ZANDSLOOT varchar2(1), DOSSIERMAP varchar2(15), IWS_W_WATPEIL number(38,8), IWS_W_WATBRREFP number(38,8), IWS_W_WATDIEPTE number(38,8), IWS_W_INSTHGTEL number(38,8), IWS_W_PLASBTALL number(38,8), IWS_W_BRPLASBL number(38,8), IWS_W_PLASBH_DL number(38,8), IWS_W_TALUDL number(38,8), IWS_W_BODBR number(38,8), IWS_W_BODHO number(38,8), WS_ONDERHOUDSMAAT number(38,8), WS_ONDERHOUDSDIEPTE number(38,8), IWS_W_TALUDR number(38,8), IWS_W_PLASBH_DR number(38,8), IWS_W_BRPLASBR number(38,8), IWS_W_PLASBTALR number(38,8), IWS_W_INSTHGTER number(38,8), OBJECTBEGINTIJD date,
      OBJECTEINDTIJD date, TIJDSTIPREGISTRATIE date, EINDREGISTRATIE date, NAAMSPACE varchar2(50), LOKAALID varchar2(50), LVPUBLICATIEDATUM date, DETAILNIVEAUGEOMETRIE number(38,8), WS_ONDH_VAAR varchar2(1), WS_SCHOUW varchar2(1), WS_MODEL varchar2(1), OPMERKING varchar2(500), WS_MAAI varchar2(1), LENGTE number(38,8), VISMIGRATIE varchar2(1), SE_ANNO_CAD_DATA blob
    -> ArcSDEGridSnapper

Bookmark: aanmaken velden Hydamo en vullen
  LET op! Hier worden aannames voor ruwheid gedaan.
AttributeKeeper_3
    KEEP_ATTRS = IWS_W_TALUDL,IWS_W_BODHO,OBJECTEINDTIJD,IWS_W_BRPLASBR,CODE,NAAM,OBJECTBEGINTIJD,IWS_W_INSTHGTEL,IWS_W_PLASBH_DL,IWS_W_TALUDR,IWS_W_PLASBTALL,IWS_W_INSTHGTER,IWS_W_BODBR,CATEGORIEOPPWATERLICHAAM,IWS_W_BRPLASBL,IWS_W_PLASBH_DR,IWS_W_PLASBTALR,STATUSOBJECT
    -> AttributeRenamer_3
AttributeRenamer_3
    ATTR_TABLE:
      RENAME_SET_DEFAULT CODE > code
      RENAME_SET_DEFAULT NAAM > naam
      RENAME_SET_DEFAULT STATUSOBJECT > statusobjectcode
      RENAME_SET_DEFAULT OBJECTBEGINTIJD > objectbegintijd
      RENAME_SET_DEFAULT OBJECTEINDTIJD > objecteindtijd
      RENAME_SET_DEFAULT IWS_W_BODHO > bodemhoogtebenedenstrooms
      RENAME_SET_DEFAULT IWS_W_BODBR > bodembreedte
      RENAME_SET_DEFAULT IWS_W_TALUDL > taludhellinglinkerzijde
      RENAME_SET_DEFAULT IWS_W_TALUDR > taludhellingrechterzijde
      RENAME_SET_DEFAULT IWS_W_PLASBH_DL > hoogteplasbermlinkerzijde
      RENAME_SET_DEFAULT IWS_W_PLASBH_DR > hoogteplasbermrechterzijde
      RENAME_SET_DEFAULT IWS_W_PLASBTALL > taludhellingplasbermlinkerzijde
      RENAME_SET_DEFAULT IWS_W_PLASBTALR > taludhellingplasbermrechterzijde
      RENAME_SET_DEFAULT IWS_W_INSTHGTEL > hoogteinsteeklinkerzijde
      RENAME_SET_DEFAULT IWS_W_INSTHGTER > hoogteinsteekrechterzijde
      RENAME_SET_DEFAULT IWS_W_BRPLASBL > breedteplasbermlinkerzijde
      RENAME_SET_DEFAULT IWS_W_BRPLASBR > breedteplasbermrechterzijde
    -> AttributeCreator_7
AttributeCreator_7
    ATTR_TABLE:
      SET_TO hyperlink
      SET_TO ruwheidstypecode = 4
      SET_TO ruwheidswaardelaag = FME_CONDITIONAL:DEFAULT_VALUE'30'BOOL_OP;OR;COMPOSITE_TEST;<Unused>;TEST @Value(CATEGORIEOPPWATERLICHAAM) = 1'35'FME_NUM_CONDITIONS2___
      SET_TO ruwheidswaardehoog = FME_CONDITIONAL:DEFAULT_VALUE'15'BOOL_OP;OR;COMPOSITE_TEST;<Unused>;TEST @Value(CATEGORIEOPPWATERLICHAAM) = 1'25'FME_NUM_CONDITIONS2___
      SET_TO administratiefgebiedcode = 17
      SET_TO bodemhoogtebovenstrooms = @Value(bodemhoogtebenedenstrooms)
    -> AttributeManager
AttributeManager
    ATTR_TABLE:
      SET_TO statusobjectcode = FME_CONDITIONAL:DEFAULT_VALUE'@Evaluate(@Value(statusobjectcode)/100)'BOOL_OP;OR;COMPOSITE_TEST;<Unused>;TEST @Value(statusobjectcode) = 9900'98'FME_NUM_CONDITIONS2___
      REMOVE CATEGORIEOPPWATERLICHAAM
    -> normgeparametriseerdprofiel (writer GML2_1)
    -> AttributeCreator_7_Output

Bookmark: output gecontroleerd tegen xsd schema
normgeparametriseerdprofiel (writer GML2_1)
    attributes: code xml_char(200), naam xml_char(200), statusobjectcode xml_char(200), objectbegintijd xml_char(200), objecteindtijd xml_char(200), hyperlink xml_char(200), bodemhoogtebenedenstrooms xml_char(200), bodemhoogtebovenstrooms xml_char(200), bodembreedte xml_char(200), taludhellinglinkerzijde xml_char(200), taludhellingrechterzijde xml_char(200), hoogteplasbermlinkerzijde xml_char(200), hoogteplasbermrechterzijde xml_char(200), breedteplasbermlinkerzijde xml_char(200), breedteplasbermrechterzijde xml_char(200), taludhellingplasbermlinkerzijde xml_char(200), taludhellingplasbermrechterzijde xml_char(200), hoogteinsteeklinkerzijde xml_char(200), hoogteinsteekrechterzijde xml_char(200), ruwheidstypecode xml_char(200), ruwheidswaardelaag xml_char(200), ruwheidswaardehoog xml_char(200), administratiefgebiedcode xml_char(200)
