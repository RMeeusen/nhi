FME workspace 02C_HyDAMO_DwarsprofielPuntenIngemeten.fmw

Parameters:
- SourceDataset_FILEGDB_4 = \\wsl-fs01\QdriveWPM\WSL\fileshare\ArcGIS_Brondata\Overige_WPM_Data\OverigeWROData.gdb   # Source Geodatabase
- SourceDataset_FILEGDB = \\wsl-app09\Sobek\HDB\Data\HDB.gdb   # Source Geodatabase
- SourceDataset_ORACLE_SPATIAL = wsl-ora30.wsl.lan/damo   # Service Name or Easy Connect
- DestDataset_FILEGDB = \\wsl-app09\Sobek\HDB\Data\HDB.gdb   # Destination Geodatabase

Readers:
- FILEGDB_1: FILEGDB from $(SourceDataset_FILEGDB_4)
- ORACLE_SPATIAL_1: ORACLE_SPATIAL from $(SourceDataset_ORACLE_SPATIAL) in Netherlands-RDNew-2008
- FILEGDB_2: FILEGDB from $(SourceDataset_FILEGDB)

Writers:
- FILEGDB_3: FILEGDB to $(DestDataset_FILEGDB)

GW_PRO (reader FILEGDB_1)
    attributes: PRO_ID objectid, PRO_TYPE text(24), MPN_MPN_ID int, IPRKS_IPRKS_ID int, PROIDENT text(24), OVK_OVK_ID int, DWK_DWK_ID int, OWA_OWA_ID int, PRO_PRO_ID int, PRW_PRW_ID int, DDPKRUIN double, DGPNUMME text(24), OPRRICHT text(13), LBISTATG text(32), DDPHWMAT single, PROSOORT text(30), DDPHWGEM single, OPRDATOP date, DDPZMRPL single, GEGBRON text(50), DDPWNTPL single, OSMOMSCH text(60), DDPOPGPL single, IWS_LEGRT text(0), DDPZETT single, TBTVWIND single, KTCSOORT text(8), DDPRRGLF single, DDPPARAP text(8), DDPITOGT single,
      DDPITOTO single, DDPTOORD text(13), DDPITEEN text(8), DDPIABKL text(8), IWS_X_OFFSET double, IWS_Y_OFFSET double, IWS_VOOR_LEN double, IWS_NA_LEN double, IWS_HYPERLINK text(240), RICHTING single, IWS_GEPEILD_DOOR text(100), IWS_DATUM_GEPEILD date, SE_ANNO_CAD_DATA blob, GEOMETRIE_Length double
    -> Tester_7
    -> GeometryFilter
Tester_7
    BOOL_OP = OR
    TEST_CLAUSE = TEST @Value(PROIDENT) BEGINS_WITH DP
    PASSED -> Tester_8
Note: Tester_8 / Test of het attribuut eindigt op 'A' / of 'B', en neemt deze niet mee aangezien / dit dwarsprofielen van bruggen zijn
Tester_8
    BOOL_OP = AND
    TEST_CLAUSE:
      TEST @Value(PROIDENT) ENDS_WITH A
      TEST @Value(PROIDENT) ENDS_WITH B
    FAILED -> Tester_4
AttributeManager_11_Output: Inspector
Dwarsprofiel: Inspector
GeometryFilter
    BREAK_AGG = No
    GEOM_PORT_NAMES = Line
WS_LANDMEETGEGEVENS (reader ORACLE_SPATIAL_1)
    attributes: OBJECTID number(38,0), WS_CODE nvarchar(24), WS_VERVALDATUM date, WS_SOORTLANDMEETLIJN nvarchar(60), WS_BRON nvarchar(50), WS_OPMERKING nvarchar(60), WS_INWINNINGSDATUM date, SE_ANNO_CAD_DATA blob, CODEHISTORIE nvarchar(24), CREATED_USER nvarchar(255), CREATED_DATE date, LAST_EDITED_USER nvarchar(255), LAST_EDITED_DATE date
    -> Tester_2
AttributeManager_Output: Inspector
Note: Attributen beschrijven zoals in NHI
AttributeManager_5
    ATTR_TABLE:
      SET_TO typeprofielcode = waterloop
      RENAME_SET_VALUE volgnummer > codevolgnummer
      REMOVE PRO_ID
      SET_TO administratiefgebied = limburg
      SET_TO ruwheidstypecode = stricklerks
      SET_TO ruwheidswaardehoog = 25
      SET_TO ruwheidswaardelaag = 15
      SET_TO statusobjectcode = gerealiseerd
    -> dwarsprofielpunten_ingemeten (writer FILEGDB_3)
dwarsprofielpunten_ingemeten (writer FILEGDB_3)
    attributes: code text(200), codevolgnummer text(200), profielcode text(200), typeprofielcode text(200), ruwheidstypecode text(200), ruwheidswaardelaag double, ruwheidswaardehoog double, administratiefgebied text(200), statusobjectcode text(200)
HYDROOBJECT: Inspector

Bookmark: Test Jaartal '
Note: Tester_4 / Test of het profiel niet ouder is dan 2000
Tester_4
    BOOL_OP = OR
    TEST_CLAUSE = TEST @Value(OPRDATOP) > 20000608000000
    PASSED -> MeasureGenerator
    PASSED -> Tester

Bookmark: Voegt de lengte van de lijn toe aan de vertexes
Note: MeasureGenerator / Meet de lengte van de lijn
MeasureGenerator
    DIM = 2
    MULT = 1
    START_VALUE = 0
    -> PointOnLineOverlayer_2 [LINE]
Note: PointOnLineOverlayer_2 / Voegt de vertex punten toe met de lijnen om de / lengte van de lijn tot dat punt toe te kunnen voegen
PointOnLineOverlayer_2
    ATTR_ACCUM_MODE = Merge Incoming
    ATTR_CONFLICT_RES = Use Original
    OV_ATTR = _overlaps
    TOLERANCE = 0.001
    POINT -> MeasureExtractor_2
    <REJECTED> -> PointOnLineOverlayer_2__Rejected_
MeasureExtractor_2
    GEOM_TYPE = Point
    MEASURE_ATTR = LijnLengte
    -> AttributeManager_10
PointOnLineOverlayer_2__Rejected_: Inspector [off]

Bookmark: Test of PRO_ID ingevuld en uniek is
Tester
    BOOL_OP = OR
    TEST_CLAUSE = TEST @Value(PRO_ID) ATTRIBUTE_HAS_VALUE ""
    PASSED -> AttributeValidator
AttributeValidator
    TABLE = PRO_ID;ATTRIBUTE_UNIQUE;<Unused>
    PASSED -> Chopper
    PASSED -> Dwarsprofiel

Bookmark: Dwarsprofiellijnenen naar punten
  Maak van de originele dwarsprofiellijnen dwarsprofielpunten
Chopper
    CHOPPED_ATTR = _chopped
    MAX_VERTICES = 1
    MODE = By Vertex
    REMNANT_ATTR = _remnant
    -> ListBuilder_2
    -> FeatureMerger_2 [REQUESTOR]

Bookmark: Test hoeveel lengteprofielen er gekruist worden (minder dan 4 wordt niet meegenomen)
Note: ListBuilder / Groepeert de Dwarsprofielpunten / op basis van het 'PRO_ID'
ListBuilder_2
    GRP_BY = PRO_ID
    LIST_NAME = _list
    -> ListElementCounter_2
Note: ListElementCounter / bepaalt hoeveel punten er in / één dwarsprofiel zitten door aantal / punten in de list te tellen
ListElementCounter_2
    CNT_ATTR = _element_count
    LIST_NAME = _list{}
    -> Tester_10
Note: Tester_4 / Test of het aantal dwarsprofiel- / punten 3 of meer is, alleen bij meer / dan drie worden ze weggeschreven / (Passed)
Tester_10
    BOOL_OP = OR
    TEST_CLAUSE = TEST @Value(_element_count) > 3
    PASSED -> ListExploder_3
Note: ListExploder_2 / Splitst de gegroepeerde / punten weer
ListExploder_3
    ATTR_ACCUM_MODE = Merge Incoming List
    ATTR_CONFLICT_RES = Use Incoming List
    INDEX_ATTR = _element_index
    LIST_ATTR = _list{}
    ELEMENTS -> AttributeManager_9
Note: AttributeManager_8 / Verwijdert onnodige attributen
AttributeManager_9
    ATTR_TABLE:
      REMOVE SE_ANNO_CAD_DATA
      REMOVE _chopped
      REMOVE _remnant
    -> FeatureMerger_2 [SUPPLIER]
Note: FeatureMerger / Voegt de punten samen met de punten / die aan de voorwaarde voldoen (minimaal 3 / punten per dwarsprofiel)
FeatureMerger_2
    ATTR_ACCUM_MODE = Merge Supplier
    ATTR_CONFLICT_RES = Use Requestor
    IGNORE_NULLS = No
    JOIN_KEYS = @Value(PRO_ID) @Value(PRO_ID) AUTO
    MERGE_TYPE = Attributes Only
    PROCESS_DUPS = No
    REJECT_NULL_MISSING_KEYS = No
    SUPPLIERS_FIRST = No
    MERGED -> PointOnLineOverlayer_2 [POINT]

Bookmark: Geef punten een opeenvolgend nummer per dwarsprofiel
Note: AttributeManager_6 / Verwijdert onnodige attributen
AttributeManager_10
    ATTR_TABLE:
      REMOVE PRO_TYPE
      REMOVE MPN_MPN_ID
      REMOVE IPRKS_IPRKS_ID
      REMOVE PROIDENT
      REMOVE OVK_OVK_ID
      REMOVE DWK_DWK_ID
      REMOVE OWA_OWA_ID
      REMOVE PRO_PRO_ID
      REMOVE PRW_PRW_ID
      REMOVE DDPKRUIN
      REMOVE DGPNUMME
      REMOVE OPRRICHT
      REMOVE LBISTATG
      REMOVE DDPHWMAT
      REMOVE PROSOORT
      REMOVE DDPHWGEM
      REMOVE OPRDATOP
      REMOVE DDPZMRPL
      REMOVE GEGBRON
      REMOVE DDPWNTPL
      REMOVE OSMOMSCH
      REMOVE DDPOPGPL
      REMOVE IWS_LEGRT
      REMOVE DDPZETT
      REMOVE TBTVWIND
      REMOVE KTCSOORT
      REMOVE DDPRRGLF
      REMOVE DDPPARAP
      REMOVE DDPITOGT
      REMOVE DDPITOTO
      REMOVE DDPTOORD
      REMOVE DDPITEEN
      REMOVE DDPIABKL
      REMOVE IWS_X_OFFSET
      REMOVE IWS_Y_OFFSET
      REMOVE IWS_VOOR_LEN
      REMOVE IWS_NA_LEN
      REMOVE IWS_HYPERLINK
      REMOVE RICHTING
      REMOVE IWS_GEPEILD_DOOR
      REMOVE IWS_DATUM_GEPEILD
      REMOVE GEOMETRIE_Length
      REMOVE _fme_validation_message
    -> Counter_5
Note: Counter_3 / Telt de punten per Dwarsprofielnummer / op volgorde van de sortering
Counter_5
    CNT_ATTR = DwarsprofielPunt_count
    DOMAIN = @Value(PRO_ID)counter
    SCOPE = Global
    START = 0
    -> AttributeManager_11
Note: AttributeManager_11 / Verwijdert onnodige attributen
AttributeManager_11
    ATTR_TABLE:
      SET_TO code = @Value(PRO_ID)_@Value(DwarsprofielPunt_count)
      RENAME_SET_VALUE DwarsprofielPunt_count > volgnummer
      SET_TO PRO_ID > profielcode = @Value(PRO_ID)
      SET_TO typeprofielcode = waterloop
      REMOVE _overlaps
      REMOVE SE_ANNO_CAD_DATA
      REMOVE _chopped
      REMOVE _remnant
      REMOVE _element_count
      REMOVE _element_index
      REMOVE LijnLengte
    -> AttributeManager_5
    -> AttributeManager_11_Output

Bookmark: Selectie zonder vervaldatum, Lengteprofiel en Taludlijn
Note: Tester_2 / Test of de Vervaldatum leeg is / en of daarmee de meetgegevens / niet al vervallen zijn
Tester_2
    BOOL_OP = OR
    TEST_CLAUSE = TEST @Value(WS_VERVALDATUM) = ""
    PASSED -> Tester_3
Note: Tester_3 / Test of de soort landmeetlijn / geen Taludlijn is, deze worden niet / meegenomen
Tester_3
    BOOL_OP = OR
    TEST_CLAUSE = TEST @Value(WS_SOORTLANDMEETLIJN) != Taludlijn
    PASSED -> Tester_6
Note: Tester_6 / Test of de soort landmeetlijn / een Dwarsprofiel is.
Tester_6
    BOOL_OP = OR
    TEST_CLAUSE = TEST @Value(WS_SOORTLANDMEETLIJN) = Dwarsprofiel oppervlaktewater
    PASSED -> MeasureGenerator_2
    PASSED -> Chopper_2
    FAILED -> Lengteprofielen
Lengteprofielen: Inspector [off]

Bookmark: Voegt de lengte van de lijn toe aan de vertexes
Note: MeasureGenerator / Meet de lengte van de lijn
MeasureGenerator_2
    DIM = 2
    MULT = 1
    START_VALUE = 0
    -> PointOnLineOverlayer_3 [LINE]
Note: PointOnLineOverlayer_2 / Voegt de vertex punten toe met de lijnen om de / lengte van de lijn tot dat punt toe te kunnen voegen
PointOnLineOverlayer_3
    ATTR_ACCUM_MODE = Merge Incoming
    ATTR_CONFLICT_RES = Use Original
    OV_ATTR = _overlaps
    TOLERANCE = 0.001
    POINT -> MeasureExtractor_3
    <REJECTED> -> PointOnLineOverlayer_2__Rejected__2
MeasureExtractor_3
    GEOM_TYPE = Point
    MEASURE_ATTR = _point_measure
    -> AttributeManager_3
PointOnLineOverlayer_2__Rejected__2: Inspector [off]

Bookmark: Dwarsprofiellijnenen naar punten
  Maak van de originele dwarsprofiellijnen dwarsprofielpunten
Chopper_2
    CHOPPED_ATTR = _chopped
    MAX_VERTICES = 1
    MODE = By Vertex
    REMNANT_ATTR = _remnant
    -> ListBuilder_3
    -> FeatureMerger_3 [REQUESTOR]

Bookmark: Test hoeveel lengteprofielen er gekruist worden (minder dan 4 wordt niet meegenomen)
Note: ListBuilder / Groepeert de Dwarsprofielpunten / op basis van het 'DwarsProfNr'
ListBuilder_3
    GRP_BY = WS_CODE
    LIST_NAME = _list
    -> ListElementCounter_3
Note: ListElementCounter / bepaalt hoeveel punten er in / één dwarsprofiel zitten door aantal / punten in de list te tellen
ListElementCounter_3
    CNT_ATTR = _element_count
    LIST_NAME = _list{}
    -> Tester_5
Note: Tester_4 / Test of het aantal dwarsprofiel- / punten 3 of meer is, alleen bij meer / dan drie worden ze weggeschreven / (Passed)
Tester_5
    BOOL_OP = OR
    TEST_CLAUSE = TEST @Value(_element_count) > 3
    PASSED -> ListExploder_2
Note: ListExploder_2 / Splitst de gegroepeerde / punten weer
ListExploder_2
    ATTR_ACCUM_MODE = Merge Incoming List
    ATTR_CONFLICT_RES = Use Incoming List
    INDEX_ATTR = _element_index
    LIST_ATTR = _list{}
    ELEMENTS -> AttributeManager_2
Note: AttributeManager_8 / Verwijdert onnodige attributen
AttributeManager_2
    ATTR_TABLE:
      REMOVE OBJECTID
      REMOVE WS_VERVALDATUM
      REMOVE WS_SOORTLANDMEETLIJN
      REMOVE WS_BRON
      REMOVE WS_OPMERKING
      REMOVE WS_INWINNINGSDATUM
      REMOVE SE_ANNO_CAD_DATA
      REMOVE CODEHISTORIE
      REMOVE CREATED_USER
      REMOVE CREATED_DATE
      REMOVE LAST_EDITED_USER
      REMOVE LAST_EDITED_DATE
      REMOVE _chopped
      REMOVE _remnant
    -> FeatureMerger_3 [SUPPLIER]
Note: FeatureMerger / Voegt de punten samen met de punten / die aan de voorwaarde voldoen (minimaal 3 / punten per dwarsprofiel)
FeatureMerger_3
    ATTR_ACCUM_MODE = Merge Supplier
    ATTR_CONFLICT_RES = Use Requestor
    IGNORE_NULLS = No
    JOIN_KEYS = @Value(WS_CODE) @Value(WS_CODE) AUTO
    MERGE_TYPE = Attributes Only
    PROCESS_DUPS = No
    REJECT_NULL_MISSING_KEYS = No
    SUPPLIERS_FIRST = No
    MERGED -> PointOnLineOverlayer_3 [POINT]

Bookmark: Geef punten een opeenvolgend nummer per dwarsprofiel
Note: AttributeManager_6 / Verwijdert onnodige attributen
AttributeManager_3
    -> Counter_2
Note: Counter_3 / Telt de punten per Dwarsprofielnummer / op volgorde van de sortering
Counter_2
    CNT_ATTR = DwarsprofielPunt_count
    DOMAIN = @Value(OBJECTID)counter
    SCOPE = Global
    START = 0
    -> AttributeManager_4
Note: AttributeManager_11 / Verwijdert onnodige attributen
AttributeManager_4
    ATTR_TABLE:
      REMOVE SE_ANNO_CAD_DATA
      RENAME_SET_VALUE OBJECTID > ObjectID
      SET_TO Code = @Value(WS_CODE)_@Value(DwarsprofielPunt_count)
      REMOVE WS_VERVALDATUM
      RENAME_SET_VALUE WS_SOORTLANDMEETLIJN > Soortlandmeetlijn
      REMOVE WS_BRON
      REMOVE WS_OPMERKING
      REMOVE WS_INWINNINGSDATUM
      REMOVE CODEHISTORIE
      REMOVE CREATED_USER
      REMOVE CREATED_DATE
      REMOVE LAST_EDITED_USER
      REMOVE LAST_EDITED_DATE
      REMOVE _chopped
      REMOVE _remnant
      REMOVE _element_count
      REMOVE _element_index
      REMOVE _point_measure
      RENAME_SET_VALUE DwarsprofielPunt_count > codevolgnummer
    -> AttributeManager
AttributeManager
    ATTR_TABLE:
      REMOVE _overlaps
      REMOVE ObjectID
      RENAME_SET_VALUE WS_CODE > profielcode
      RENAME_SET_VALUE Code > code
      REMOVE Soortlandmeetlijn
    -> AttributeManager_5
    -> AttributeManager_Output

Bookmark: Wat is dit? Waarom is dit in een GDB gezet?
HYDROOBJECT (reader FILEGDB_2)
    attributes: Code text(75), Administatiefgebiedid text(75), Ruwheidstypecode text(75), Ruwheidswaardelaag text(75), Ruwheidswaardehoog text(75), Naam text(75), StatusObjectCode text(75), DatumStatusObject text(75), DatumRealisatieObject text(75), LeggerStatus text(75), InModel text(75), OBJECTID objectid
    -> HYDROOBJECT

Bookmark: Test GW PRO data
Note: Tester_7 / Test of het om een Dwarsprofiel / of een Lengteprofiel gaat
