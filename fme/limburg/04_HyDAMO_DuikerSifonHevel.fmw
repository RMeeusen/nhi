FME workspace 04_HyDAMO_DuikerSifonHevel.fmw

Parameters:
- DestDataset_FILEGDB_23 = \\wsl-app09\Sobek\HDB\Data\HDB.gdb   # Destination Geodatabase
- DestDataset_FILEGDB_19 = \\wsl-app09\Sobek\HDB\Data\HDBTerugkoppelingDAMO.gdb   # Destination Geodatabase
- DestDataset_FILEGDB_27 = \\wsl-app09\Sobek\HDB\Data\HDBTerugkoppelingDAMO.gdb   # Destination Geodatabase
- SourceDataset_ORACLE_SPATIAL_9 = wsl-ora30.wsl.lan\damo   # Service Name or Easy Connect

Readers:
- ORACLE_SPATIAL_1: ORACLE_SPATIAL from $(SourceDataset_ORACLE_SPATIAL_9) in Netherlands-RDNew-2008

Writers:
- FILEGDB_1: FILEGDB to $(DestDataset_FILEGDB_23)
- FILEGDB_2: FILEGDB to $(DestDataset_FILEGDB_19)
- FILEGDB_3: FILEGDB to $(DestDataset_FILEGDB_27)

Note: DAMO_W.HYDROOBJECT: damo [ORACLE_SPATIAL] / Import vanuit DAMO, ook wel Waterlopen genoemd
HYDROOBJECT (reader ORACLE_SPATIAL_1)
    attributes: OBJECTID number(38,0), SE_ANNO_CAD_DATA blob, CODE nvarchar(50), NAAM nvarchar(100), STATUSLEGGERWATERSYSTEEM number(5,0), STATUSLEGGERWATERVEILIGHEID number(5,0), STATUSOBJECT number(5,0), HYPERLINK nvarchar(100), OPMERKING nvarchar(250), SOORTOPPWATERKWALITEIT number(3,0), SOORTOPPWATERKWANTITEIT number(3,0), CATEGORIEOPPWATERLICHAAM number(3,0), BREEDTE number(8,2), LENGTE number(8,2), DRAINEERT number(10,0), GETIJDEBEINVLOED nvarchar(1), NIVEAU number(3,0), ONTSTAANSWIJZE number(3,0), OPPWATERVOLGNUMMER number(8,0), RUIMTELIJKEAFBAKENINGBEKEND nvarchar(1), PERSISTENTIE number(3,0), OPPERVLAKTEWATERLICHAAMID number(10,0), METADATAID number(10,0), HYDROOBJECTDEELID number(10,0), KRWSTROMENDID number(10,0), VAARWEGID number(10,0), MEETLOCATIEID number(10,0), TIJDSTIPREGISTRATIE date, OBJECTBEGINTIJD date, OBJECTEINDTIJD date,
      LOKAALID nvarchar(50), NAMESPACE nvarchar(50), DETAILNIVEAUGEOMETRIE number(10,0), LVPUBLICATIEDATUM date, WS_LEGGERPRODUCT nvarchar(10), WS_VASTSTELLINGLEGGER date, WS_VOLUME number(12,0), WS_AANLEGJAAR nvarchar(4), WS_BERGENDVERMWINTER number(12,0), WS_BERGENDVERMZOMER number(12,0), CODEHISTORIE nvarchar(50), CREATED_USER nvarchar(255), CREATED_DATE date, LAST_EDITED_USER nvarchar(255), LAST_EDITED_DATE date, GLOBALID char(38), WS_VERGUNNINGNUMMER nvarchar(50)
    -> Bufferer
Note: DAMO_W.DUIKERSIFONHEVEL: damo [ORACLE_SPATIAL] / Input vanuit DAMO
DUIKERSIFONHEVEL (reader ORACLE_SPATIAL_1)
    attributes: OBJECTID number(38,0), SE_ANNO_CAD_DATA blob, CODE nvarchar(50), NAAM nvarchar(100), STATUSLEGGERWATERSYSTEEM number(5,0), STATUSLEGGERWATERVEILIGHEID number(5,0), STATUSOBJECT number(5,0), HYPERLINK nvarchar(100), OPMERKING nvarchar(250), INDICATIEWATERKEREND number(5,0), KERENDEHOOGTE number(8,2), TYPEWATERKERENDECONSTRUCTIE number(5,0), INDPEILREGULPEILSCHEIDEND nvarchar(1), CATEGORIE number(5,0), LENGTE number(8,2), HOOGTEOPENING number(8,2), BREEDTEOPENING number(8,2), HOOGTEBINNENONDERKANTBENE number(8,2), DREMPELPEIL number(8,2), HOOGTEBINNENONDERKANTBOV number(8,2), SIGNALERINGSPEIL number(8,2), VORMKOKER number(3,0), SLUITPEIL number(8,2), SOORTMATERIAAL number(3,0), OPENKEERPEIL number(8,2), OPENINGSPEIL number(8,2), REGENWATERBUFFERCOMPARTIMENTID number(10,0), TYPEKRUISING number(3,0), WATERKERINGID number(10,0), METADATAID number(10,0),
      TIJDSTIPREGISTRATIE date, OBJECTBEGINTIJD date, OBJECTEINDTIJD date, LOKAALID nvarchar(50), NAMESPACE nvarchar(50), DETAILNIVEAUGEOMETRIE number(10,0), LVPUBLICATIEDATUM date, WS_AANLEGJAAR nvarchar(4), WS_AANTALIDENTIEKEBUIZEN number(2,0), WS_BODEMHOOGTEBENEDEN number(8,2), WS_BODEMHOOGTEBOVEN number(8,2), WS_VPO_IDNR number(10,0), WS_FRONTVLEUGELMUURBOVEN nvarchar(1), WS_LEGGERPRODUCT nvarchar(10), WS_VASTSTELLINGLEGGER date, WS_FRONTVLEUGELMUURBENE nvarchar(1), WS_KOMBERGING number(6,2), WS_AANTALPUTTEN number(5,0), WS_WANDDIKTE number(3,2), WS_VOLDOETNENLKW nvarchar(24), WS_VERGUNNINGNUMMER nvarchar(50), WS_UITSTROOMVOORZIENING number(6,2), WS_STAATVANONDERHOUD number(5,0), WS_SOORTDUIKER number(2,0), WS_PLAATSELIJKEAANDUIDING nvarchar(50), WS_ONTWERPBUITENWATERSTAND number(6,2), WS_ONDERHOUDSPLICHTIGE nvarchar(50), WS_KMRAAIMAAS number(5,0), WS_INSTROOMVOORZIENING number(6,2), WS_GEMWATERSTAND number(6,2),
      WS_DIJKPAAL nvarchar(50), WS_BRON nvarchar(100), WS_AFSTANDTOTDIJKPAAL number(5,0), WS_AFSLUITINGBOVENSTROOMS number(2,0), WS_AFSLUITINGBENEDENSTROOMS number(2,0), WS_AFSLUITBAAR nvarchar(10), CODEHISTORIE nvarchar(50), WS_SAMENGESTELDKUNSTWERK nvarchar(24), CREATED_USER nvarchar(255), CREATED_DATE date, LAST_EDITED_USER nvarchar(255), LAST_EDITED_DATE date, GLOBALID char(38)
    -> AttributeManager_7

Bookmark: 4.3 Controle DSH ligt op HydroObject met een marge van (zie onderstaand)
Note: Bufferer / Voegt een marge toe rond de HydroObjecten / van10 cm
Bufferer
    CAP_STYLE = Round
    INTERP_SEGMENTS = 8
    OFFSET = 0.1
    BUFFERED -> AttributeRemover_2
AttributeRemover_2
    REMOVE_ATTRS = SOORTOPPWATERKWANTITEIT,WS_BERGENDVERMZOMER,GLOBALID,LENGTE,BREEDTE,OBJECTEINDTIJD,NIVEAU,METADATAID,ONTSTAANSWIJZE,STATUSLEGGERWATERVEILIGHEID,VAARWEGID,LAST_EDITED_USER,WS_VASTSTELLINGLEGGER,LVPUBLICATIEDATUM,DETAILNIVEAUGEOMETRIE,OBJECTBEGINTIJD,OBJECTID,WS_VERGUNNINGNUMMER,KRWSTROMENDID,OPPWATERVOLGNUMMER,PERSISTENTIE,HYDROOBJECTDEELID,RUIMTELIJKEAFBAKENINGBEKEND,WS_BERGENDVERMWINTER,CREATED_USER,GETIJDEBEINVLOED,STATUSOBJECT,WS_VOLUME,LOKAALID,CREATED_DATE,NAMESPACE,CODE,DRAINEERT,CODEHISTORIE,CATEGORIEOPPWATERLICHAAM,OPMERKING,TIJDSTIPREGISTRATIE,STATUSLEGGERWATERSYSTEEM,LAST_EDITED_DATE,NAAM,OPPERVLAKTEWATERLICHAAMID,WS_AANLEGJAAR,SOORTOPPWATERKWALITEIT,HYPERLINK,MEETLOCATIEID,WS_LEGGERPRODUCT,SE_ANNO_CAD_DATA
    -> SpatialFilter [Filter]
Note: SpatialFilter / Test of de HydroObjecten en de / DSF's een overlap hebben / - Wel Overlap -> Passed / - Geen Overlap -> Failed
SpatialFilter
    AGGREGATE_HANDLING = Yes
    ATTR_ACCUM_MODE = Prefix Filter
    ATTR_PREFIX = HO
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager_8
    PASSED -> SpatialFilter_Passed
    FAILED -> AttributeManager_9
    <REJECTED> -> AttributeManager_10
SpatialFilter_Passed: Inspector

Bookmark: 4.1 Bewerking 1
Note: AttributeManager_7 / Onnodige attributen worden / verwijderd
Note: De volgende attributen / worden toegevoegd (leeg!): / - SoortKokervormigeConstructiecode / - RuwheidstypeCode / - Ruwheidswaarde / - Intreeverlies / - Uittreeverlies / - DatumStatusObject / - IndicatiePeilregulerendPeilscheidend
AttributeManager_7
    ATTR_TABLE:
      RENAME_SET_VALUE CODE > Code = D_@Value(Code)
      REMOVE LENGTE
      RENAME_SET_VALUE HOOGTEOPENING > HoogteOpening
      RENAME_SET_VALUE BREEDTEOPENING > BreedteOpening
      RENAME_SET_VALUE HOOGTEBINNENONDERKANTBENE > HoogteBinnenonderkantBenedenstrooms
      RENAME_SET_VALUE HOOGTEBINNENONDERKANTBOV > HoogteBinnenonderkantBovenstrooms
      RENAME_SET_VALUE VORMKOKER > VormKokercode
      SET_TO SoortKokervormigeConstructiecode
      SET_TO RuwheidstypeCode
      SET_TO Ruwheidswaarde
      SET_TO Intreeverlies
      SET_TO Uittreeverlies
      RENAME_SET_VALUE STATUSOBJECT > StatusObject
      SET_TO DatumStatusObject
      RENAME_SET_VALUE OBJECTBEGINTIJD > DatumRealisatieObject
      REMOVE OBJECTID
      RENAME_SET_VALUE WS_AFSLUITINGBOVENSTROOMS > AfsluitmiddelCode_Bovenstrooms
      RENAME_SET_VALUE WS_AFSLUITINGBENEDENSTROOMS > AfsluitmiddelCode_Benedenstrooms
      REMOVE NAAM
      REMOVE SE_ANNO_CAD_DATA
      REMOVE STATUSLEGGERWATERSYSTEEM
      REMOVE STATUSLEGGERWATERVEILIGHEID
      REMOVE HYPERLINK
      REMOVE OPMERKING
      REMOVE INDICATIEWATERKEREND
      REMOVE KERENDEHOOGTE
      REMOVE TYPEWATERKERENDECONSTRUCTIE
      RENAME_SET_VALUE INDPEILREGULPEILSCHEIDEND > IndicatiePeilregulerendPeilscheidend
      REMOVE CATEGORIE
      REMOVE DREMPELPEIL
      REMOVE SIGNALERINGSPEIL
      REMOVE SLUITPEIL
      REMOVE SOORTMATERIAAL
      REMOVE OPENKEERPEIL
      REMOVE OPENINGSPEIL
      REMOVE REGENWATERBUFFERCOMPARTIMENTID
      REMOVE TYPEKRUISING
      REMOVE WATERKERINGID
      REMOVE METADATAID
      REMOVE TIJDSTIPREGISTRATIE
      REMOVE OBJECTEINDTIJD
      REMOVE LOKAALID
      REMOVE NAMESPACE
      REMOVE DETAILNIVEAUGEOMETRIE
      REMOVE LVPUBLICATIEDATUM
      REMOVE WS_AANLEGJAAR
      REMOVE WS_AANTALIDENTIEKEBUIZEN
      REMOVE WS_BODEMHOOGTEBENEDEN
      REMOVE WS_BODEMHOOGTEBOVEN
      REMOVE WS_VPO_IDNR
      REMOVE WS_FRONTVLEUGELMUURBOVEN
      REMOVE WS_LEGGERPRODUCT
      REMOVE WS_VASTSTELLINGLEGGER
      REMOVE WS_FRONTVLEUGELMUURBENE
      REMOVE WS_KOMBERGING
      REMOVE WS_AANTALPUTTEN
      REMOVE WS_WANDDIKTE
      REMOVE WS_VOLDOETNENLKW
      REMOVE WS_VERGUNNINGNUMMER
      REMOVE WS_UITSTROOMVOORZIENING
      REMOVE WS_STAATVANONDERHOUD
      REMOVE WS_SOORTDUIKER
      REMOVE WS_PLAATSELIJKEAANDUIDING
      REMOVE WS_ONTWERPBUITENWATERSTAND
      REMOVE WS_ONDERHOUDSPLICHTIGE
      REMOVE WS_KMRAAIMAAS
      REMOVE WS_INSTROOMVOORZIENING
      REMOVE WS_GEMWATERSTAND
      REMOVE WS_DIJKPAAL
      REMOVE WS_BRON
      REMOVE WS_AFSTANDTOTDIJKPAAL
      REMOVE WS_AFSLUITBAAR
      REMOVE CODEHISTORIE
      REMOVE WS_SAMENGESTELDKUNSTWERK
      REMOVE CREATED_USER
      REMOVE CREATED_DATE
      REMOVE LAST_EDITED_USER
      REMOVE LAST_EDITED_DATE
      REMOVE GLOBALID
    -> Tester_14

Bookmark: 4.1.1. Bewerking StatusObject
Note: Tester_14 / Test of het attribuut 'StatusObject / een waarde heeft
Tester_14
    BOOL_OP = OR
    TEST_CLAUSE = TEST @Value(StatusObject) ATTRIBUTE_HAS_VALUE ""
    PASSED -> AttributeManager_50_OUTPUT_-__Tester_7
    FAILED -> AttributeManager_50
Note: AttributeManager_50 / Wanneer 'StatusObject' / geen waarde heeft wordt hier de / waarde 98 aan gegeven (code / voor missende waarde)
AttributeManager_50
    ATTR_TABLE = SET_TO StatusObject = 98
    -> AttributeManager_50_OUTPUT_-__Tester_7
AttributeManager_50_OUTPUT_-__Tester_7: Junction
    -> Tester_7

Bookmark: 4.2 Check op naam en code
Note: Tester / Volledigheid van de gegevens, test of: / - Code heeft een waarde / Als het dit heeft -> Passed / Zo niet -> Failed
Tester_7
    BOOL_OP = OR
    TEST_CLAUSE = TEST @Value(Code) ATTRIBUTE_HAS_VALUE ""
    PASSED -> AttributeValidator_3
    FAILED -> AttributeManager_36
Note: AttributeValidator / Checkt of de Code uniek is / Is dit het geval -> Passed / Zo niet -> Failed
AttributeValidator_3
    TABLE = Code;ATTRIBUTE_UNIQUE;<Unused>
    PASSED -> SpatialFilter [Candidate]
    FAILED -> AttributeManager_36

Bookmark: 4. DuikerSifonHevel
Note: AttributeManager_9 / Deze DSH's liggen niet op een HydroObject (ook / niet met de marge in de check hiervoor)
AttributeManager_9
    -> LengthCalculator_2
AttributeManager_10
    -> LengthCalculator_2
Note: AttributeManager_8 / Behoudt alleen de attributen van de / DSH's
AttributeManager_8
    ATTR_TABLE:
      SET_TO VormKokercode = FME_CONDITIONAL:DEFAULT_VALUE'onbekend'BOOL_OP;OR;COMPOSITE_TEST;<Unused>;TEST @Value(VormKokercode) = 1'rond'BOOL_OP;OR;COMPOSITE_TEST;<Unused>;TEST @Value(VormKokercode) = 2'driehoekig'BOOL_OP;OR;COMPOSITE_TEST;<Unused>;TEST @Value(VormKokercode) = 3'rechthoekig'BOOL_OP;OR;COMPOSITE_TEST;<Unused>;TEST @Value(VormKokercode) = 4'eivormig'BOOL_OP;OR;COMPOSITE_TEST;<Unused>;TEST @Value(VormKokercode) = 5'ellipsvormig'BOOL_OP;OR;COMPOSITE_TEST;<Unused>;TEST @Value(VormKokercode) = 6'paraboolvormig'BOOL_OP;OR;COMPOSITE_TEST;<Unused>;TEST @Value(VormKokercode) = 7'trapeziumvormig'BOOL_OP;OR;COMPOSITE_TEST;<Unused>;TEST @Value(VormKokercode) = 8'heulprofiel'BOOL_OP;OR;COMPOSITE_TEST;<Unused>;TEST @Value(VormKokercode) = 9'muilprofiel'BOOL_OP;OR;COMPOSITE_TEST;<Unused>;TEST @Value(VormKokercode) = 10'langwerpig'BOOL_OP;OR;COMPOSITE_TEST;<Unused>;TEST @Value(VormKokercode) = 11'scherp'FME_NUM_CONDITIONS12___
      SET_TO SoortKokervormigeConstructiecode = FME_CONDITIONAL:DEFAULT_VALUE'duiker'BOOL_OP;OR;COMPOSITE_TEST;<Unused>;TEST @Value(SoortKokervormigeConstructiecode) = 1'duiker'BOOL_OP;OR;COMPOSITE_TEST;<Unused>;TEST @Value(SoortKokervormigeConstructiecode) = 2'hevel'BOOL_OP;OR;COMPOSITE_TEST;<Unused>;TEST @Value(SoortKokervormigeConstructiecode) = 3'sifon'FME_NUM_CONDITIONS4___
      SET_TO RuwheidstypeCode = stricklerks
      SET_TO Ruwheidswaarde = 60
      SET_TO Intreeverlies = 0,5
      SET_TO Uittreeverlies = 1
      RENAME_SET_VALUE StatusObject > statusobjectcode = FME_CONDITIONAL:DEFAULT_VALUE'onbekend'BOOL_OP;OR;COMPOSITE_TEST;<Unused>;TEST @Value(statusobjectcode) = 1'planvorming'BOOL_OP;OR;COMPOSITE_TEST;<Unused>;TEST @Value(statusobjectcode) = 3'gerealiseerd'BOOL_OP;OR;COMPOSITE_TEST;<Unused>;TEST @Value(statusobjectcode) = 4'buiten bedrijf'BOOL_OP;OR;COMPOSITE_TEST;<Unused>;TEST @Value(statusobjectcode) = 5'niet meer aanwezig'BOOL_OP;OR;COMPOSITE_TEST;<Unused>;TEST @Value(statusobjectcode) = 7'te verwijderen'FME_NUM_CONDITIONS6___
      SET_TO IndicatiePeilregulerendPeilscheidend > indpeilregulpeilscheidend = FME_CONDITIONAL:DEFAULT_VALUE'@Value(IndicatiePeilregulerendPeilscheidend)'BOOL_OP;OR;COMPOSITE_TEST;<Unused>;TEST IndicatiePeilregulerendPeilscheidend ATTRIBUTE_VALUE_NULL _FME_BLANK_STRING_'o'FME_NUM_CONDITIONS2___
      REMOVE _predicate
      REMOVE _fme_validation_message
      SET_TO administratiefgebied = limburg
    -> LengthCalculator
    -> AttributeManager_8_Output
AttributeManager_8_Output: Inspector

Bookmark: 4.5.1 Bewerking 4
Note: LengthCalculator / Berekend de lengte
LengthCalculator_2
    DIM = 2
    LEN_ATTR = Lengte
    MULT = 1
    -> AttributeRounder_2
    <REJECTED> -> AttributeRounder_2
Note: AttributeRounder / Rond de lengte af op 2 decimalen
AttributeRounder_2
    PLACES = 2
    ROUND_TYPE = Nearest
    SRC_ATTRS = Lengte
    -> DUIKERSIFONHEVEL_BuitenHydroObject (writer FILEGDB_2)
    -> AttributeManager_29
    <REJECTED> -> DUIKERSIFONHEVEL_BuitenHydroObject (writer FILEGDB_2)

Bookmark: 4.6.1 Output naar FileGDB TerugkoppelingDAMO
Note: DAMO_W_DUIKERSIFONHEVEL: TerugkoppelingDAMO [FILEGDB] - 2 / Schrijft de DuikerSifonHevels weg in een File Geodatabase als punten. / (alleen de DSH's die niet binnen 10cm van een HydroObject liggen.
DUIKERSIFONHEVEL_BuitenHydroObject (writer FILEGDB_2)
    attributes: Code text(75), HoogteOpening text(75), BreedteOpening text(75), HoogteBinnenonderkantBenedenstrooms text(75), HoogteBinnenonderkantBovenstrooms text(75), VormKokercode text(75), SoortKokervormigeConstructiecode text(75), RuwheidstypeCode text(75), Ruwheidswaarde text(75), Intreeverlies text(75), Uittreeverlies text(75), StatusObject text(75), DatumStatusObject text(75), DatumRealisatieObject text(75), IndicatiePeilregulerendPeilscheidend text(75), AfsluitmiddelCode_Bovenstrooms text(75), AfsluitmiddelCode_Benedenstrooms text(75), _fme_validation_message text(75), fme_rejection_code text(75), Lengte text(75)
Note: DUIKERSIFONHEVEL_MissendeWaardes: HDBTerugkoppelingDAMO [FILEGDB] - 6 / Schrijft alle DSH's weg in een File Geodatabase als punten. / Dit inclusief het attribuut 'MissendeWaardes' waarin is aangegeven / hoeveel attributen vanuit DAMO geen waarde hebben.
DUIKERSIFONHEVEL_MissendeWaardes (writer FILEGDB_3)
    attributes: Code text(75), HoogteOpening text(75), BreedteOpening text(75), HoogteBinnenonderkantBenedenstrooms text(75), HoogteBinnenonderkantBovenstrooms text(75), VormKokercode text(75), SoortKokervormigeConstructiecode text(75), RuwheidstypeCode text(75), Ruwheidswaarde text(75), Intreeverlies text(75), Uittreeverlies text(75), StatusObject text(75), DatumStatusObject text(75), DatumRealisatieObject text(75), IndicatiePeilregulerendPeilscheidend text(75), AfsluitmiddelCode_Bovenstrooms text(75), AfsluitmiddelCode_Benedenstrooms text(75), fme_rejection_code text(75), Lengte text(75), MissendeWaardes text(75)

Bookmark: 4.5.1 Bewerking 3
Note: LengthCalculator / Berekend de lengte
LengthCalculator
    DIM = 2
    LEN_ATTR = Lengte
    MULT = 1
    -> AttributeRounder
Note: AttributeRounder / Rond de lengte af op 2 decimalen
AttributeRounder
    PLACES = 2
    ROUND_TYPE = Nearest
    SRC_ATTRS = Lengte
    -> duikersifonhevel (writer FILEGDB_1)
    -> AttributeManager_29

Bookmark: 4.6 Controle missende waardes
AttributeManager_29
    ATTR_TABLE:
      SET_TO MissendeWaardes = 0
      REMOVE _fme_validation_message
    -> Tester_HoogteOpening
Note: Tester_HoogteOpening
Tester_HoogteOpening
    BOOL_OP = OR
    TEST_CLAUSE = TEST @Value(HoogteOpening) ATTRIBUTE_HAS_VALUE ""
    PASSED -> Tester_BreedteOpening
    FAILED -> AttributeManager_30
AttributeManager_30
    ATTR_TABLE = SET_TO MissendeWaardes = @add(@Value(MissendeWaardes),1)
    -> Tester_BreedteOpening
Note: Alle testers in deze bookmark testen of het attribuut waar ze op testen (staat er dikgedrukt boven) een waarde heeft. Wanneer dit niet het geval is dan krijgt het attribuut 'MissendeWaardes' een waarde van +1.
Note: Tester_BreedteOpening
Tester_BreedteOpening
    BOOL_OP = OR
    TEST_CLAUSE = TEST @Value(BreedteOpening) ATTRIBUTE_HAS_VALUE ""
    PASSED -> Tester_HoogteBinnenonderkantBenedenstrooms
    FAILED -> AttributeManager_31
AttributeManager_31
    ATTR_TABLE = SET_TO MissendeWaardes = @add(@Value(MissendeWaardes),1)
    -> Tester_HoogteBinnenonderkantBenedenstrooms
Note: Tester_HoogteBinnenonderkantBenedenstrooms
Tester_HoogteBinnenonderkantBenedenstrooms
    BOOL_OP = OR
    TEST_CLAUSE = TEST @Value(HoogteBinnenonderkantBenedenstrooms) ATTRIBUTE_HAS_VALUE ""
    PASSED -> Tester_HoogteBinnenonderkantBovenstrooms
    FAILED -> AttributeManager_32
AttributeManager_32
    ATTR_TABLE = SET_TO MissendeWaardes = @add(@Value(MissendeWaardes),1)
    -> Tester_HoogteBinnenonderkantBovenstrooms
Note: Tester_HoogteBinnenonderkantBovenstrooms
Tester_HoogteBinnenonderkantBovenstrooms
    BOOL_OP = OR
    TEST_CLAUSE = TEST @Value(HoogteBinnenonderkantBovenstrooms) = ""
    PASSED -> Tester_VormKokercode
    FAILED -> AttributeManager_33
AttributeManager_33
    ATTR_TABLE = SET_TO MissendeWaardes = @add(@Value(MissendeWaardes),1)
    -> Tester_VormKokercode
Note: Tester_VormKokercode
Tester_VormKokercode
    BOOL_OP = OR
    TEST_CLAUSE = TEST @Value(VormKokercode) ATTRIBUTE_HAS_VALUE ""
    PASSED -> Tester_StatusObject_2
    FAILED -> AttributeManager_34
AttributeManager_34
    ATTR_TABLE = SET_TO MissendeWaardes = @add(@Value(MissendeWaardes),1)
    -> Tester_StatusObject_2
Note: Tester_StatusObject_2
Tester_StatusObject_2
    BOOL_OP = OR
    TEST_CLAUSE = TEST @Value(StatusObject) ATTRIBUTE_HAS_VALUE ""
    PASSED -> AttributeManager_36
    FAILED -> AttributeManager_35
AttributeManager_35
    ATTR_TABLE = SET_TO MissendeWaardes = @add(@Value(MissendeWaardes),1)
    -> AttributeManager_36
AttributeManager_36
    -> DUIKERSIFONHEVEL_MissendeWaardes (writer FILEGDB_3)

Bookmark: 4.6.2 Output naar FileGDB HydrologischeDatabase
Note: DAMO_W_DUIKERSIFONHEVEL: HydrologischeDatabase [FILEGDB] - 4 / Schrijft de DuikerSifonHevels weg in een File Geodatabase als punten. / (alleen de DSH's binnen 50cm van een HydroObject
duikersifonhevel (writer FILEGDB_1)
    attributes: code text(75), hoogteopening double, breedteopening double, hoogtebinnenonderkantbenedenstrooms double, hoogtebinnenonderkantbovenstrooms double, vormkokercode text(75), soortkokervormigeconstructiecode text(75), ruwheidstypecode text(75), ruwheidswaarde double, intreeverlies double, uittreeverlies double, statusobjectcode text(75), indpeilregulpeilscheidend text(75), lengte double, administratiefgebied text(75)
