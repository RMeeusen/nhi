FME workspace 06_HyDAMO_Bodemval.fmw

Parameters:
- DestDataset_FILEGDB_30 = \\wsl-app09\Sobek\HDB\Data\HDB.gdb   # Destination Geodatabase
- SourceDataset_ORACLE_SPATIAL_9 = wsl-ora30.wsl.lan\damo   # Service Name or Easy Connect
- DestDataset_FILEGDB = N:\HDB\Data\HDBTerugkoppelingDAMO.gdb   # Destination Geodatabase

Readers:
- ORACLE_SPATIAL_1: ORACLE_SPATIAL from $(SourceDataset_ORACLE_SPATIAL_9) in Netherlands-RDNew-2008

Writers:
- FILEGDB_1: FILEGDB to $(DestDataset_FILEGDB_30) in Netherlands-RDNew-2008
- FILEGDB_2: FILEGDB to $(DestDataset_FILEGDB)

Note: DAMO_W.BODEMVAL: damo [ORACLE_SPATIAL] / Input vanuit DAMO
BODEMVAL (reader ORACLE_SPATIAL_1)
    attributes: OBJECTID number(38,0), SE_ANNO_CAD_DATA blob, CODE nvarchar(50), NAAM nvarchar(100), STATUSLEGGERWATERSYSTEEM number(5,0), STATUSLEGGERWATERVEILIGHEID number(5,0), STATUSOBJECT number(5,0), HYPERLINK nvarchar(100), OPMERKING nvarchar(250), RICHTING number(5,2), BODEMHOOGTEBENEDENSTROOMS number(8,2), METADATAID number(10,0), BODEMHOOGTEBOVENSTROOMS number(8,2), BREEDTE number(8,2), TIJDSTIPREGISTRATIE date, OBJECTBEGINTIJD date, OBJECTEINDTIJD date, LOKAALID nvarchar(50), NAMESPACE nvarchar(50), DETAILNIVEAUGEOMETRIE number(10,0), LVPUBLICATIEDATUM date, WS_AANLEGJAAR nvarchar(4), WS_VASTSTELLINGLEGGER date, WS_SOORTMATERIAAL number(3,0), WS_PLAATSELIJKEAANDUIDING nvarchar(50), WS_LEGGERPRODUCT nvarchar(10), WS_VPO_IDNR number(10,0), WS_VERGUNBAAR nvarchar(3), WS_VERDEDIGING nvarchar(12), WS_LENGTE number(4,2),
      WS_EIGENAAR nvarchar(1), WS_SOORT number(2,0), WS_VERGUNNINGNUMMER nvarchar(50), WS_KERENDEHOOGTE number(7,3), CODEHISTORIE nvarchar(50), CREATED_USER nvarchar(255), CREATED_DATE date, LAST_EDITED_USER nvarchar(255), LAST_EDITED_DATE date, GLOBALID char(38)
    -> AttributeManager_11
Note: DAMO_W.HYDROOBJECT: damo [ORACLE_SPATIAL] / Import vanuit DAMO, ook wel Waterlopen genoemd
HYDROOBJECT (reader ORACLE_SPATIAL_1)
    attributes: OBJECTID number(38,0), SE_ANNO_CAD_DATA blob, CODE nvarchar(50), NAAM nvarchar(100), STATUSLEGGERWATERSYSTEEM number(5,0), STATUSLEGGERWATERVEILIGHEID number(5,0), STATUSOBJECT number(5,0), HYPERLINK nvarchar(100), OPMERKING nvarchar(250), SOORTOPPWATERKWALITEIT number(3,0), SOORTOPPWATERKWANTITEIT number(3,0), CATEGORIEOPPWATERLICHAAM number(3,0), BREEDTE number(8,2), LENGTE number(8,2), DRAINEERT number(10,0), GETIJDEBEINVLOED nvarchar(1), NIVEAU number(3,0), ONTSTAANSWIJZE number(3,0), OPPWATERVOLGNUMMER number(8,0), RUIMTELIJKEAFBAKENINGBEKEND nvarchar(1), PERSISTENTIE number(3,0), OPPERVLAKTEWATERLICHAAMID number(10,0), METADATAID number(10,0), HYDROOBJECTDEELID number(10,0), KRWSTROMENDID number(10,0), VAARWEGID number(10,0), MEETLOCATIEID number(10,0), TIJDSTIPREGISTRATIE date, OBJECTBEGINTIJD date, OBJECTEINDTIJD date,
      LOKAALID nvarchar(50), NAMESPACE nvarchar(50), DETAILNIVEAUGEOMETRIE number(10,0), LVPUBLICATIEDATUM date, WS_LEGGERPRODUCT nvarchar(10), WS_VASTSTELLINGLEGGER date, WS_VOLUME number(12,0), WS_AANLEGJAAR nvarchar(4), WS_BERGENDVERMWINTER number(12,0), WS_BERGENDVERMZOMER number(12,0), CODEHISTORIE nvarchar(50), CREATED_USER nvarchar(255), CREATED_DATE date, LAST_EDITED_USER nvarchar(255), LAST_EDITED_DATE date, GLOBALID char(38), WS_VERGUNNINGNUMMER nvarchar(50)
    -> AttributeRemover_3

Bookmark: 6.1 Aanmaken nieuwe attributen, testen op StatusObject
Note: AttributeManager_11 / Onnodige attributen worden / verwijderd
Note: De volgende attributen / worden toegevoegd (leeg!): / - DwarsprofielBovenstrooms / - DwarsprofielBenedenstrooms / - DatumStatusObject
AttributeManager_11
    ATTR_TABLE:
      SET_TO CODE > Code = BV_@Value(CODE)
      SET_TO DwarsprofielBovenstrooms
      SET_TO DwarsprofielBenedenstrooms
      SET_TO AdministratiefGebied = NL.60.60
      RENAME_SET_VALUE BODEMHOOGTEBOVENSTROOMS > Bodemhoogtebovenstrooms
      RENAME_SET_VALUE BODEMHOOGTEBENEDENSTROOMS > Bodemhoogtebenedenstrooms
      RENAME_SET_VALUE STATUSOBJECT > StatusObject
      SET_TO DatumStatusObject
      RENAME_SET_VALUE OBJECTBEGINTIJD > DatumRealisatieObject
      RENAME_SET_VALUE WS_AANLEGJAAR > Aanlegjaar
      REMOVE OBJECTID
      REMOVE SE_ANNO_CAD_DATA
      REMOVE NAAM
      REMOVE STATUSLEGGERWATERSYSTEEM
      REMOVE STATUSLEGGERWATERVEILIGHEID
      REMOVE HYPERLINK
      REMOVE OPMERKING
      REMOVE RICHTING
      REMOVE METADATAID
      REMOVE BREEDTE
      REMOVE TIJDSTIPREGISTRATIE
      REMOVE OBJECTEINDTIJD
      REMOVE LOKAALID
      REMOVE NAMESPACE
      REMOVE DETAILNIVEAUGEOMETRIE
      REMOVE LVPUBLICATIEDATUM
      REMOVE WS_VASTSTELLINGLEGGER
      REMOVE WS_SOORTMATERIAAL
      REMOVE WS_PLAATSELIJKEAANDUIDING
      REMOVE WS_LEGGERPRODUCT
      REMOVE WS_VPO_IDNR
      REMOVE WS_VERGUNBAAR
      REMOVE WS_VERDEDIGING
      REMOVE WS_LENGTE
      REMOVE WS_EIGENAAR
      REMOVE WS_SOORT
      REMOVE WS_VERGUNNINGNUMMER
      REMOVE WS_KERENDEHOOGTE
      REMOVE CODEHISTORIE
      REMOVE CREATED_USER
      REMOVE CREATED_DATE
      REMOVE LAST_EDITED_USER
      REMOVE LAST_EDITED_DATE
      REMOVE GLOBALID
    -> Tester_15
Note: Tester_15 / Test of StatusObject een code heeft, / stuurt alle missende waardes door naar de / attributemanager
Tester_15
    BOOL_OP = OR
    TEST_CLAUSE = TEST @Value(StatusObject) ATTRIBUTE_HAS_VALUE ""
    PASSED -> AttributeManager_51_OUTPUT_-__Tester_10
    FAILED -> AttributeManager_51
Note: AttributeManager_51 / Geeft bij StatusObject (missend) de waarde 98
AttributeManager_51
    ATTR_TABLE = SET_TO StatusObject = 98
    -> AttributeManager_51_OUTPUT_-__Tester_10
AttributeManager_51_OUTPUT_-__Tester_10: Junction
    -> Tester_10

Bookmark: 6.2 Check op naam en code
Note: Tester / Volledigheid van de gegevens, test of: / - Code heeft een waarde / Als het dit heeft -> Passed / Zo niet -> Failed
Tester_10
    BOOL_OP = OR
    TEST_CLAUSE = TEST @Value(Code) ATTRIBUTE_HAS_VALUE ""
    PASSED -> AttributeValidator_5
    FAILED -> AttributeManager_44
Note: AttributeValidator / Checkt of de Code uniek is / Is dit het geval -> Passed / Zo niet -> Failed
AttributeValidator_5
    TABLE = Code;ATTRIBUTE_UNIQUE;<Unused>
    PASSED -> Tester_5
    FAILED -> AttributeManager_44

Bookmark: 6.3 Samenvoegen DatumRealisatieObject en Aanlegjaar
Note: Tester_5 / Test of DatumRealisatieObject gevuld is
Tester_5
    BOOL_OP = OR
    TEST_CLAUSE = TEST @Value(DatumRealisatieObject) ATTRIBUTE_HAS_VALUE ""
    PASSED -> AttributeManager_73_OUTPUT_-__PointOnLineOverlayer_3_POINT
    FAILED -> AttributeManager_73
Note: AttributeManager_73 / Wanneer DatumRealisatieObject leeg is / wordt de waarde van attribuut Aanglegjaar / toegeveogd
AttributeManager_73
    ATTR_TABLE = SET_TO DatumRealisatieObject = @Value(Aanlegjaar)
    -> AttributeManager_73_OUTPUT_-__PointOnLineOverlayer_3_POINT

Bookmark: 6.3 Controle ligt de bodemval op een HydroObject
AttributeManager_73_OUTPUT_-__PointOnLineOverlayer_3_POINT: Junction
    -> PointOnLineOverlayer_3 [POINT]
Note: AttributeRemover_3 / Verwijdert onnodige attributen / van HydroObject
AttributeRemover_3
    REMOVE_ATTRS = LAST_EDITED_DATE,ONTSTAANSWIJZE,OBJECTEINDTIJD,WS_BERGENDVERMZOMER,CODEHISTORIE,WS_BERGENDVERMWINTER,WS_AANLEGJAAR,WS_VOLUME,GLOBALID,NAAM,WS_LEGGERPRODUCT,OPMERKING,CREATED_DATE,DETAILNIVEAUGEOMETRIE,CATEGORIEOPPWATERLICHAAM,SOORTOPPWATERKWALITEIT,TIJDSTIPREGISTRATIE,VAARWEGID,MEETLOCATIEID,PERSISTENTIE,OBJECTBEGINTIJD,BREEDTE,DRAINEERT,HYPERLINK,OPPWATERVOLGNUMMER,OBJECTID,METADATAID,NIVEAU,STATUSLEGGERWATERVEILIGHEID,SOORTOPPWATERKWANTITEIT,GETIJDEBEINVLOED,LAST_EDITED_USER,LENGTE,STATUSOBJECT,STATUSLEGGERWATERSYSTEEM,CREATED_USER,SE_ANNO_CAD_DATA,CODE,RUIMTELIJKEAFBAKENINGBEKEND,KRWSTROMENDID,OPPERVLAKTEWATERLICHAAMID,LVPUBLICATIEDATUM,HYDROOBJECTDEELID,LOKAALID,NAMESPACE,WS_VASTSTELLINGLEGGER,WS_VERGUNNINGNUMMER
    -> PointOnLineOverlayer_3 [LINE]
Note: PointOnLineOverlayer_2 / Controleert of de bodemval op een HydroObject ligt / met een marge van 1cm. / Wanneer dit zo is krijgt de nieuwe attribuut 'Overlap' / een waare van 1 of hoger (bij overlap met meerdere HydroObjecten).
PointOnLineOverlayer_3
    ATTR_ACCUM_MODE = Merge Incoming
    ATTR_CONFLICT_RES = Use Original
    OV_ATTR = Overlaps
    TOLERANCE = 0.01
    POINT -> Tester_11
Note: Tester_8 / Controleert of de Overlap 1 of groter is / Indien dit zo is -> Passed / Indien dit niet zo is -> Failed
Tester_11
    BOOL_OP = OR
    TEST_CLAUSE = TEST @Value(Overlaps) >= 1
    PASSED -> AttributeManager_40
    FAILED -> AttributeManager_41

Bookmark: 6.4 Verwijdering onnodige attributen, samenvoegen DatumRealisatieObject en Aanlegjaar
Note: AttributeManager_13 / Onnodige attributen worden / verwijderd
AttributeManager_41
    ATTR_TABLE:
      REMOVE CODE
      REMOVE Aanlegjaar
      REMOVE _fme_validation_message
    -> AttributeManager_42
    -> BODEMVAL_BuitenHydroObject (writer FILEGDB_2)
Note: AttributeManager_12 / Onnodige attributen worden / verwijderd
AttributeManager_40
    ATTR_TABLE:
      SET_TO StatusObject > StatusObjectcode = FME_CONDITIONAL:DEFAULT_VALUE'onbekend'BOOL_OP;OR;COMPOSITE_TEST;<Unused>;TEST @Value(StatusObject) = 1'planvorming'BOOL_OP;OR;COMPOSITE_TEST;<Unused>;TEST @Value(StatusObject) = 3'gerealiseerd'BOOL_OP;OR;COMPOSITE_TEST;<Unused>;TEST @Value(StatusObject) = 4'buiten bedrijf'BOOL_OP;OR;COMPOSITE_TEST;<Unused>;TEST @Value(StatusObject) = 5'niet meer aanwezig'BOOL_OP;OR;COMPOSITE_TEST;<Unused>;TEST @Value(StatusObject) = 7'te verwijderen'FME_NUM_CONDITIONS6___
      REMOVE CODE
      REMOVE _fme_validation_message
      SET_TO AdministratiefGebied = limburg
    -> AttributeManager_42
    -> bodemval (writer FILEGDB_1)

Bookmark: 6.6.1 Output naar FileGDB 'HDBterugkoppelingDAMO
BODEMVAL_BuitenHydroObject (writer FILEGDB_2) [off]
    attributes: Code text(75), DwarsprofielBovenstrooms text(75), DwarsprofielBenedenstrooms text(75), StatusObject text(75), DatumStatusObject text(75), DatumRealisatieObject text(75), Overlaps text(75), Bodemhoogtebovenstrooms text(75), Bodemhoogtebenedenstrooms text(75), AdministratiefGebied text(75)
BODEMVAL_MissendeWaardes (writer FILEGDB_2) [off]
    attributes: Code text(75), DwarsprofielBovenstrooms text(75), DwarsprofielBenedenstrooms text(75), StatusObject text(75), DatumStatusObject text(75), DatumRealisatieObject text(75), Overlaps text(75), MissendeWaardes text(75), Bodemhoogtebovenstrooms text(75), Bodemhoogtebenedenstrooms text(75), Aanlegjaar text(75), AdministratiefGebied text(75)

Bookmark: 6.5 Controle missende waardes
Note: Alle testers in deze bookmark testen of het attribuut waar ze op testen (staat er dikgedrukt boven) een waarde heeft. Wanneer dit niet het geval is dan krijgt het attribuut 'MissendeWaardes' een waarde van +1.
AttributeManager_42
    ATTR_TABLE = SET_TO MissendeWaardes = 0
    -> Tester_StatusObject_3
Note: Tester_StatusObject_3
Tester_StatusObject_3
    BOOL_OP = OR
    TEST_CLAUSE = TEST @Value(StatusObject) ATTRIBUTE_HAS_VALUE ""
    PASSED -> Tester_DatumStatusObject_2
    FAILED -> AttributeManager_43
AttributeManager_43
    ATTR_TABLE = SET_TO MissendeWaardes = @add(@Value(MissendeWaardes),1)
    -> Tester_DatumStatusObject_2
Note: Tester_DatumStatusObject_2
Tester_DatumStatusObject_2
    BOOL_OP = OR
    TEST_CLAUSE = TEST @Value(DatumStatusObject) ATTRIBUTE_HAS_VALUE ""
    PASSED -> AttributeManager_44
    FAILED -> AttributeManager_72
AttributeManager_72
    ATTR_TABLE = SET_TO MissendeWaardes = @add(@Value(MissendeWaardes),1)
    -> AttributeManager_44
AttributeManager_44
    ATTR_TABLE:
      REMOVE CODE
      REMOVE _fme_validation_message_list{}
      REMOVE _fme_validation_message
    -> BODEMVAL_MissendeWaardes (writer FILEGDB_2)

Bookmark: 6.6.2 Output naar FileGDB 'HDB'
Note: BODEMVAL: HDB [FILEGDB] - 5 / Schrijft de Bodemvallen weg in een File Geodatabase als punten. / (alleen de Bodemvallen binnen 1cm van een HydroObject
bodemval (writer FILEGDB_1)
    attributes: code text(75), dwarsprofielbovenstrooms text(75), dwarsprofielbenedenstrooms text(75), statusobjectcode text(75), administratiefgebied text(75)
