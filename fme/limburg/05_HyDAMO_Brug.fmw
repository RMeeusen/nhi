FME workspace 05_HyDAMO_Brug.fmw

Parameters:
- DestDataset_FILEGDB_29 = \\wsl-app09\Sobek\HDB\Data\HDB.gdb   # Destination Geodatabase
- DestDataset_FILEGDB_21 = N:\HDB\Data\HDBTerugkoppelingDAMO.gdb   # Destination Geodatabase
- SourceDataset_ORACLE_SPATIAL_9 = wsl-ora30.wsl.lan\damo   # Service Name or Easy Connect

Readers:
- ORACLE_SPATIAL_1: ORACLE_SPATIAL from $(SourceDataset_ORACLE_SPATIAL_9) in Netherlands-RDNew-2008

Writers:
- FILEGDB_1: FILEGDB to $(DestDataset_FILEGDB_29)
- FILEGDB_2: FILEGDB to $(DestDataset_FILEGDB_21)

Note: DAMO_W.HYDROOBJECT: damo [ORACLE_SPATIAL] / Import vanuit DAMO, ook wel Waterlopen genoemd
HYDROOBJECT (reader ORACLE_SPATIAL_1)
    attributes: OBJECTID number(38,0), SE_ANNO_CAD_DATA blob, CODE nvarchar(50), NAAM nvarchar(100), STATUSLEGGERWATERSYSTEEM number(5,0), STATUSLEGGERWATERVEILIGHEID number(5,0), STATUSOBJECT number(5,0), HYPERLINK nvarchar(100), OPMERKING nvarchar(250), SOORTOPPWATERKWALITEIT number(3,0), SOORTOPPWATERKWANTITEIT number(3,0), CATEGORIEOPPWATERLICHAAM number(3,0), BREEDTE number(8,2), LENGTE number(8,2), DRAINEERT number(10,0), GETIJDEBEINVLOED nvarchar(1), NIVEAU number(3,0), ONTSTAANSWIJZE number(3,0), OPPWATERVOLGNUMMER number(8,0), RUIMTELIJKEAFBAKENINGBEKEND nvarchar(1), PERSISTENTIE number(3,0), OPPERVLAKTEWATERLICHAAMID number(10,0), METADATAID number(10,0), HYDROOBJECTDEELID number(10,0), KRWSTROMENDID number(10,0), VAARWEGID number(10,0), MEETLOCATIEID number(10,0), TIJDSTIPREGISTRATIE date, OBJECTBEGINTIJD date, OBJECTEINDTIJD date,
      LOKAALID nvarchar(50), NAMESPACE nvarchar(50), DETAILNIVEAUGEOMETRIE number(10,0), LVPUBLICATIEDATUM date, WS_LEGGERPRODUCT nvarchar(10), WS_VASTSTELLINGLEGGER date, WS_VOLUME number(12,0), WS_AANLEGJAAR nvarchar(4), WS_BERGENDVERMWINTER number(12,0), WS_BERGENDVERMZOMER number(12,0), CODEHISTORIE nvarchar(50), CREATED_USER nvarchar(255), CREATED_DATE date, LAST_EDITED_USER nvarchar(255), LAST_EDITED_DATE date, GLOBALID char(38), WS_VERGUNNINGNUMMER nvarchar(50)
    -> PointOnLineOverlayer_2 [LINE]
Note: DAMO_W.BRUG: damo [ORACLE_SPATIAL] / Import vanuit DAMO
BRUG (reader ORACLE_SPATIAL_1)
    attributes: OBJECTID number(38,0), SE_ANNO_CAD_DATA blob, CODE nvarchar(50), NAAM nvarchar(100), STATUSLEGGERWATERSYSTEEM number(5,0), STATUSLEGGERWATERVEILIGHEID number(5,0), STATUSOBJECT number(5,0), HYPERLINK nvarchar(100), OPMERKING nvarchar(250), SOORTOVERSPANNING number(3,0), HOOGTEONDERZIJDE number(8,2), DOORVAARTBREEDTE number(8,2), RICHTING number(5,2), HOOGTECONSTRUCTIE number(8,2), METADATAID number(10,0), SOORTMATERIAAL number(3,0), TYPEKRUISING number(3,0), TIJDSTIPREGISTRATIE date, OBJECTBEGINTIJD date, OBJECTEINDTIJD date, LOKAALID nvarchar(50), NAMESPACE nvarchar(50), DETAILNIVEAUGEOMETRIE number(10,0), LVPUBLICATIEDATUM date, WS_VERGUNBAAR nvarchar(3), WS_VPO_IDNR number(10,0), WS_VERDEDIGING nvarchar(12), WS_SOORTMATERIAALDEK number(3,0), WS_PLAATSELIJKEAANDUIDING nvarchar(50), WS_LENGTE number(8,2),
      WS_KERENDEHOOGTE number(8,2), WS_BREEDTE number(8,2), WS_BODEMHOOGTEBRUGBOVEN number(8,2), WS_AANLEGJAAR nvarchar(4), WS_BODEMHOOGTEBRUGBENEDEN number(8,2), CODEHISTORIE nvarchar(50), CREATED_USER nvarchar(255), CREATED_DATE date, LAST_EDITED_USER nvarchar(255), LAST_EDITED_DATE date, GLOBALID char(38), WS_VERGUNNINGNUMMER nvarchar(50)
    -> Attributemanager_11

Bookmark: 5.1 Bewerking 1
Note: AttributeManager_11 / Onnodige attributen worden / verwijderd
Note: De volgende attributen / worden toegevoegd (leeg!): / - Dwarsprofielcode / - Ruwheidstypecode / - Ruwheidswaarde / - Intreeverlies / - Uittreeverlies
Attributemanager_11: AttributeManager
    ATTR_TABLE:
      RENAME_SET_VALUE CODE > Code = B_@Value(Code)
      RENAME_SET_VALUE HOOGTEONDERZIJDE > Hoogteonderzijde
      SET_TO Dwarsprofielcode
      SET_TO Ruwheidstypecode = StricklerKs
      SET_TO Ruwheidswaarde = 25
      SET_TO Intreeverlies = 0,25
      SET_TO Uittreeverlies = 0,25
      REMOVE OBJECTID
      REMOVE SE_ANNO_CAD_DATA
      REMOVE NAAM
      REMOVE STATUSLEGGERWATERSYSTEEM
      REMOVE STATUSLEGGERWATERVEILIGHEID
      REMOVE STATUSOBJECT
      REMOVE HYPERLINK
      REMOVE OPMERKING
      REMOVE SOORTOVERSPANNING
      REMOVE DOORVAARTBREEDTE
      REMOVE RICHTING
      REMOVE HOOGTECONSTRUCTIE
      REMOVE METADATAID
      REMOVE SOORTMATERIAAL
      REMOVE TYPEKRUISING
      REMOVE TIJDSTIPREGISTRATIE
      REMOVE OBJECTBEGINTIJD
      REMOVE OBJECTEINDTIJD
      REMOVE LOKAALID
      REMOVE NAMESPACE
      REMOVE DETAILNIVEAUGEOMETRIE
      REMOVE LVPUBLICATIEDATUM
      REMOVE WS_VERGUNBAAR
      REMOVE WS_VPO_IDNR
      REMOVE WS_VERDEDIGING
      REMOVE WS_SOORTMATERIAALDEK
      REMOVE WS_PLAATSELIJKEAANDUIDING
      REMOVE WS_LENGTE
      REMOVE WS_KERENDEHOOGTE
      REMOVE WS_BREEDTE
      REMOVE WS_BODEMHOOGTEBRUGBOVEN
      REMOVE WS_AANLEGJAAR
      REMOVE WS_BODEMHOOGTEBRUGBENEDEN
      REMOVE CODEHISTORIE
      REMOVE CREATED_USER
      REMOVE CREATED_DATE
      REMOVE LAST_EDITED_USER
      REMOVE LAST_EDITED_DATE
      REMOVE GLOBALID
      REMOVE WS_VERGUNNINGNUMMER
    -> Tester_9

Bookmark: 5.2 Check op naam en code
Note: Tester / Volledigheid van de gegevens, test of: / - Code heeft een waarde / Als het dit heeft -> Passed / Zo niet -> Failed
Tester_9
    BOOL_OP = OR
    TEST_CLAUSE = TEST @Value(Code) ATTRIBUTE_HAS_VALUE ""
    PASSED -> AttributeValidator_4
    FAILED -> AttributeManager_39
Note: AttributeValidator / Checkt of de Code uniek is / Is dit het geval -> Passed / Zo niet -> Failed
AttributeValidator_4
    TABLE = Code;ATTRIBUTE_UNIQUE;<Unused>
    PASSED -> Tester_12
    FAILED -> AttributeManager_39

Bookmark: NEW Check op hoogte (boven NAP)
Tester_12
    BOOL_OP = OR
    TEST_CLAUSE:
      TEST @Value(Hoogteonderzijde) >= 8
      TEST Hoogteonderzijde ATTRIBUTE_VALUE_NULL ""
    PASSED -> LengthCalculator_3
    FAILED -> AttributeManager_46

Bookmark: 5.3 Bewerking 2
Note: LengthCalculator_3 / Berekend de lengte de Brug op basis van / de Polyline in RD New
LengthCalculator_3
    DIM = 2
    LEN_ATTR = Lengte
    MULT = 1
    -> AttributeRounder_3
Note: AttributeRounder_3 / Rond de lengte af op twee decimalen
AttributeRounder_3
    PLACES = 2
    ROUND_TYPE = Nearest
    SRC_ATTRS = Lengte
    -> PointOnLineOverlayer_2 [POINT]

Bookmark: 5.4 Controle ligt de brug op een HydroObject
Note: PointOnLineOverlayer_2 / Controleert of de brug op een HydroObject ligt / met een marge van 1cm. / Wanneer dit zo is krijgt de nieuwe attribuut 'Overlap' / een waare van 1 of hoger (bij overlap met meerdere HydroObjecten).
PointOnLineOverlayer_2
    ATTR_ACCUM_MODE = Merge Incoming
    ATTR_CONFLICT_RES = Use Original
    OV_ATTR = _overlaps
    TOLERANCE = 0.01
    POINT -> Tester_8
    <REJECTED> -> AttributeManager_39
Note: Tester_8 / Controleert of de Overlap 1 of groter is / Indien dit zo is -> Passed / Indien dit niet zo is -> Failed
Tester_8
    BOOL_OP = OR
    TEST_CLAUSE = TEST @Value(_overlaps) >= 1
    PASSED -> AttributeManager_12
    PASSED -> AttributeManager_37
    FAILED -> AttributeManager_13
    FAILED -> AttributeManager_37

Bookmark: 5.5 Controle missende waardes
Note: Alle testers in deze bookmark testen of het attribuut waar ze op testen (staat er dikgedrukt boven) een waarde heeft. Wanneer dit niet het geval is dan krijgt het attribuut 'MissendeWaardes' een waarde van +1.
AttributeManager_37
    ATTR_TABLE = SET_TO MissendeWaardes = 0
    -> Tester_Hoogteonderzijde
Note: Tester_Hoogteonderzijde
Tester_Hoogteonderzijde
    BOOL_OP = OR
    TEST_CLAUSE = TEST @Value(Hoogteonderzijde) ATTRIBUTE_HAS_VALUE ""
    PASSED -> AttributeManager_39
    FAILED -> AttributeManager_38
AttributeManager_38
    ATTR_TABLE = SET_TO MissendeWaardes = @add(@Value(MissendeWaardes),1)
    -> AttributeManager_39

Bookmark: 5.6 Output
AttributeManager_39
    ATTR_TABLE:
      REMOVE _fme_validation_message_list{}
      REMOVE _fme_validation_message
      REMOVE OBJECTID
      REMOVE SE_ANNO_CAD_DATA
      REMOVE CODE
      REMOVE NAAM
      REMOVE STATUSLEGGERWATERSYSTEEM
      REMOVE STATUSLEGGERWATERVEILIGHEID
      REMOVE STATUSOBJECT
      REMOVE HYPERLINK
      REMOVE OPMERKING
      REMOVE SOORTOPPWATERKWALITEIT
      REMOVE SOORTOPPWATERKWANTITEIT
      REMOVE CATEGORIEOPPWATERLICHAAM
      REMOVE BREEDTE
      REMOVE LENGTE
      REMOVE DRAINEERT
      REMOVE GETIJDEBEINVLOED
      REMOVE NIVEAU
      REMOVE ONTSTAANSWIJZE
      REMOVE OPPWATERVOLGNUMMER
      REMOVE RUIMTELIJKEAFBAKENINGBEKEND
      REMOVE PERSISTENTIE
      REMOVE OPPERVLAKTEWATERLICHAAMID
      REMOVE METADATAID
      REMOVE HYDROOBJECTDEELID
      REMOVE KRWSTROMENDID
      REMOVE VAARWEGID
      REMOVE MEETLOCATIEID
      REMOVE TIJDSTIPREGISTRATIE
      REMOVE OBJECTBEGINTIJD
      REMOVE OBJECTEINDTIJD
      REMOVE LOKAALID
      REMOVE NAMESPACE
      REMOVE DETAILNIVEAUGEOMETRIE
      REMOVE LVPUBLICATIEDATUM
      REMOVE WS_LEGGERPRODUCT
      REMOVE WS_VASTSTELLINGLEGGER
      REMOVE WS_VOLUME
      REMOVE WS_AANLEGJAAR
      REMOVE WS_BERGENDVERMWINTER
      REMOVE WS_BERGENDVERMZOMER
      REMOVE CODEHISTORIE
      REMOVE CREATED_USER
      REMOVE CREATED_DATE
      REMOVE LAST_EDITED_USER
      REMOVE LAST_EDITED_DATE
      REMOVE GLOBALID
      REMOVE WS_VERGUNNINGNUMMER
      REMOVE _overlaps
      REMOVE fme_rejection_code
    -> BRUG_MissendeWaardes (writer FILEGDB_2)

Bookmark: 5.6.1 Output naar FileGDB 'HDBterugkoppelingDAMO'
Note: Brug_MissendeWaardes_ja: HDBTerugkoppelingDAMO [FILEGDB] - 1 / Schrijft alle bruggen weg in een File Geodatabase als punten. / Dit inclusief het attribuut 'MissendeWaardes' waarin is aangegeven / hoeveel attributen vanuit DAMO geen waarde hebben.
BRUG_MissendeWaardes (writer FILEGDB_2)
    attributes: Code text(75), Hoogteonderzijde text(75), Dwarsprofielcode text(75), Lengte text(75), Ruwheidstypecode text(75), Ruwheidswaarde text(75), Intreeverlies text(75), Uittreeverlies text(75), MissendeWaardes text(75)
Note: BRUG_BuitenHydroObject: HDBTerugkoppelingDAMO [FILEGDB] - 2 / Schrijft de Bruggen weg in een File Geodatabase als punten. / (alleen de Bruggen die niet binnen 1cm van een HydroObject liggen
BRUG_BuitenHydroObject (writer FILEGDB_2)
    attributes: Code text(75), Hoogteonderzijde text(75), Dwarsprofielcode text(75), Lengte text(75), Ruwheidstypecode text(75), Ruwheidswaarde text(75), Intreeverlies text(75), Uittreeverlies text(75)
Note: BRUG_FoutieveHoogte_ja: HDBTerugkoppelingDAMO [FILEGDB] / Schrijft de Bruggen weg in een File Geodatabase als punten. / (alleen de Bruggen met een foutieve hoogte onder 8 meter
BRUG_FoutieveHoogte (writer FILEGDB_2)
    attributes: Code text(200), Hoogteonderzijde text(200), Dwarsprofielcode text(200), Ruwheidstypecode text(200), Ruwheidswaarde text(200), Intreeverlies text(200), Uittreeverlies text(200)

Bookmark: 5.4 Bewerking 3
Note: AttributeManager_13 - Objecten buiten HydroObject / Onnodige attributen worden / verwijderd
AttributeManager_13
    ATTR_TABLE:
      REMOVE OBJECTID
      REMOVE _overlaps
      REMOVE SE_ANNO_CAD_DATA
      REMOVE CODE
      REMOVE NAAM
      REMOVE STATUSLEGGERWATERSYSTEEM
      REMOVE STATUSLEGGERWATERVEILIGHEID
      REMOVE STATUSOBJECT
      REMOVE HYPERLINK
      REMOVE OPMERKING
      REMOVE SOORTOPPWATERKWALITEIT
      REMOVE SOORTOPPWATERKWANTITEIT
      REMOVE CATEGORIEOPPWATERLICHAAM
      REMOVE BREEDTE
      REMOVE LENGTE
      REMOVE DRAINEERT
      REMOVE GETIJDEBEINVLOED
      REMOVE NIVEAU
      REMOVE ONTSTAANSWIJZE
      REMOVE OPPWATERVOLGNUMMER
      REMOVE RUIMTELIJKEAFBAKENINGBEKEND
      REMOVE PERSISTENTIE
      REMOVE OPPERVLAKTEWATERLICHAAMID
      REMOVE METADATAID
      REMOVE HYDROOBJECTDEELID
      REMOVE KRWSTROMENDID
      REMOVE VAARWEGID
      REMOVE MEETLOCATIEID
      REMOVE TIJDSTIPREGISTRATIE
      REMOVE OBJECTBEGINTIJD
      REMOVE OBJECTEINDTIJD
      REMOVE LOKAALID
      REMOVE NAMESPACE
      REMOVE DETAILNIVEAUGEOMETRIE
      REMOVE LVPUBLICATIEDATUM
      REMOVE WS_LEGGERPRODUCT
      REMOVE WS_VASTSTELLINGLEGGER
      REMOVE WS_VOLUME
      REMOVE WS_AANLEGJAAR
      REMOVE WS_BERGENDVERMWINTER
      REMOVE WS_BERGENDVERMZOMER
      REMOVE CODEHISTORIE
      REMOVE CREATED_USER
      REMOVE CREATED_DATE
      REMOVE LAST_EDITED_USER
      REMOVE LAST_EDITED_DATE
      REMOVE GLOBALID
      REMOVE WS_VERGUNNINGNUMMER
      REMOVE _fme_validation_message
    -> BRUG_BuitenHydroObject (writer FILEGDB_2)
Note: AttributeManager_12 - Objecten op een HydroObject / Onnodige attributen worden / verwijderd
AttributeManager_12
    ATTR_TABLE:
      SET_TO Ruwheidstypecode = stricklerks
      REMOVE OBJECTID
      REMOVE _overlaps
      REMOVE SE_ANNO_CAD_DATA
      REMOVE CODE
      REMOVE NAAM
      REMOVE STATUSLEGGERWATERSYSTEEM
      REMOVE STATUSLEGGERWATERVEILIGHEID
      RENAME_SET_VALUE STATUSOBJECT > StatusObject = FME_CONDITIONAL:DEFAULT_VALUE'onbekend'BOOL_OP;OR;COMPOSITE_TEST;<Unused>;TEST @Value(StatusObject) = 1'planvorming'BOOL_OP;OR;COMPOSITE_TEST;<Unused>;TEST @Value(StatusObject) = 3'gerealiseerd'BOOL_OP;OR;COMPOSITE_TEST;<Unused>;TEST @Value(StatusObject) = 4'buiten bedrijf'BOOL_OP;OR;COMPOSITE_TEST;<Unused>;TEST @Value(StatusObject) = 5'niet meer aanwezig'BOOL_OP;OR;COMPOSITE_TEST;<Unused>;TEST @Value(StatusObject) = 7'te verwijderen'FME_NUM_CONDITIONS6___
      REMOVE HYPERLINK
      REMOVE OPMERKING
      REMOVE SOORTOPPWATERKWALITEIT
      REMOVE SOORTOPPWATERKWANTITEIT
      REMOVE CATEGORIEOPPWATERLICHAAM
      REMOVE BREEDTE
      REMOVE LENGTE
      REMOVE DRAINEERT
      REMOVE GETIJDEBEINVLOED
      REMOVE NIVEAU
      REMOVE ONTSTAANSWIJZE
      REMOVE OPPWATERVOLGNUMMER
      REMOVE RUIMTELIJKEAFBAKENINGBEKEND
      REMOVE PERSISTENTIE
      REMOVE OPPERVLAKTEWATERLICHAAMID
      REMOVE METADATAID
      REMOVE HYDROOBJECTDEELID
      REMOVE KRWSTROMENDID
      REMOVE VAARWEGID
      REMOVE MEETLOCATIEID
      REMOVE TIJDSTIPREGISTRATIE
      REMOVE OBJECTBEGINTIJD
      REMOVE OBJECTEINDTIJD
      REMOVE LOKAALID
      REMOVE NAMESPACE
      REMOVE DETAILNIVEAUGEOMETRIE
      REMOVE LVPUBLICATIEDATUM
      REMOVE WS_LEGGERPRODUCT
      REMOVE WS_VASTSTELLINGLEGGER
      REMOVE WS_VOLUME
      REMOVE WS_AANLEGJAAR
      REMOVE WS_BERGENDVERMWINTER
      REMOVE WS_BERGENDVERMZOMER
      REMOVE CODEHISTORIE
      REMOVE CREATED_USER
      REMOVE CREATED_DATE
      REMOVE LAST_EDITED_USER
      REMOVE LAST_EDITED_DATE
      REMOVE GLOBALID
      REMOVE WS_VERGUNNINGNUMMER
      REMOVE _fme_validation_message
      SET_TO administratiefgebied = limburg
    -> brug (writer FILEGDB_1)
Note: AttributeManager_46 - Objecten met foutieve hoogte / Onnodige attributen worden verwijderd
AttributeManager_46
    ATTR_TABLE = REMOVE _fme_validation_message
    -> BRUG_FoutieveHoogte (writer FILEGDB_2)

Bookmark: 5.6.2 Output naar FileGDB 'HDB'
Note: BRUG: HDB [FILEGDB] - 4 / Schrijft de Bruggen weg in een File Geodatabase als punten. / (alleen de DSH's binnen 1cm van een HydroObject
brug (writer FILEGDB_1)
    attributes: code text(75), hoogteonderzijde text(75), dwarsprofielcode text(75), lengte text(75), ruwheidstypecode text(75), ruwheidswaarde text(75), intreeverlies text(75), uittreeverlies text(75), statusobjectcode text(75), hoogtebovenzijde text(75), administratiefgebied text(75)
