FME workspace 01_HyDAMO_HydroObject.fmw

Parameters:
- DestDataset_FILEGDB_33 = \\wsl-app09\Sobek\HDB\Data\HDB.gdb   # Destination Geodatabase
- DestDataset_FILEGDB_25 = \\wsl-app09\Sobek\HDB\Data\HDBTerugkoppelingDAMO.gdb   # Destination Geodatabase
- SourceDataset_ORACLE_SPATIAL_9 = wsl-ora30.wsl.lan\damo   # Service Name or Easy Connect

Readers:
- ORACLE_SPATIAL_1: ORACLE_SPATIAL from $(SourceDataset_ORACLE_SPATIAL_9) in Netherlands-RDNew-2008

Writers:
- FILEGDB_1: FILEGDB to $(DestDataset_FILEGDB_33)
- FILEGDB_2: FILEGDB to $(DestDataset_FILEGDB_25)

Note: DAMO_W.HYDROOBJECT: damo [ORACLE_SPATIAL] / Import vanuit DAMO, ook wel Waterlopen genoemd
HYDROOBJECT (reader ORACLE_SPATIAL_1)
    attributes: OBJECTID number(38,0), SE_ANNO_CAD_DATA blob, CODE nvarchar(50), NAAM nvarchar(100), STATUSLEGGERWATERSYSTEEM number(5,0), STATUSLEGGERWATERVEILIGHEID number(5,0), STATUSOBJECT number(5,0), HYPERLINK nvarchar(100), OPMERKING nvarchar(250), SOORTOPPWATERKWALITEIT number(3,0), SOORTOPPWATERKWANTITEIT number(3,0), CATEGORIEOPPWATERLICHAAM number(3,0), BREEDTE number(8,2), LENGTE number(8,2), DRAINEERT number(10,0), GETIJDEBEINVLOED nvarchar(1), NIVEAU number(3,0), ONTSTAANSWIJZE number(3,0), OPPWATERVOLGNUMMER number(8,0), RUIMTELIJKEAFBAKENINGBEKEND nvarchar(1), PERSISTENTIE number(3,0), OPPERVLAKTEWATERLICHAAMID number(10,0), METADATAID number(10,0), HYDROOBJECTDEELID number(10,0), KRWSTROMENDID number(10,0), VAARWEGID number(10,0), MEETLOCATIEID number(10,0), TIJDSTIPREGISTRATIE date, OBJECTBEGINTIJD date, OBJECTEINDTIJD date,
      LOKAALID nvarchar(50), NAMESPACE nvarchar(50), DETAILNIVEAUGEOMETRIE number(10,0), LVPUBLICATIEDATUM date, WS_LEGGERPRODUCT nvarchar(10), WS_VASTSTELLINGLEGGER date, WS_VOLUME number(12,0), WS_AANLEGJAAR nvarchar(4), WS_BERGENDVERMWINTER number(12,0), WS_BERGENDVERMZOMER number(12,0), CODEHISTORIE nvarchar(50), CREATED_USER nvarchar(255), CREATED_DATE date, LAST_EDITED_USER nvarchar(255), LAST_EDITED_DATE date, GLOBALID char(38), WS_VERGUNNINGNUMMER nvarchar(50)
    -> AttributeManagerHydroObject

Bookmark: 1.1 Bewerking
Note: AttributeManager / Behoudt alleen de nodige attributen vanuit Input
Note: De volgende attributen / worden toegevoegd (leeg!): / - DatumRealisatieObject / - DatumStatusObject / De volgende attributen / worden toegevoegd met / standaard waarde: / - Administratiefgebiedid / (waarde NL.60.60)
AttributeManagerHydroObject
    ATTR_TABLE:
      RENAME_SET_VALUE CODE > Code = W_@Value(Code)
      SET_TO Administatiefgebiedid = NL.60.60
      RENAME_SET_VALUE NAAM > Naam
      RENAME_SET_VALUE STATUSLEGGERWATERSYSTEEM > LeggerStatus
      REMOVE STATUSLEGGERWATERVEILIGHEID
      RENAME_SET_VALUE STATUSOBJECT > StatusObjectCode
      SET_TO DatumRealisatieObject
      SET_TO DatumStatusObject
      REMOVE HYPERLINK
      REMOVE OPMERKING
      REMOVE SOORTOPPWATERKWALITEIT
      REMOVE SOORTOPPWATERKWANTITEIT
      REMOVE CATEGORIEOPPWATERLICHAAM
      REMOVE BREEDTE
      REMOVE LENGTE
      REMOVE DRAINEERT
      REMOVE GETIJDEBEINVLOED
      REMOVE NIVEAU
      REMOVE ONTSTAANSWIJZE
      REMOVE OPPWATERVOLGNUMMER
      REMOVE RUIMTELIJKEAFBAKENINGBEKEND
      REMOVE PERSISTENTIE
      REMOVE OPPERVLAKTEWATERLICHAAMID
      REMOVE METADATAID
      REMOVE HYDROOBJECTDEELID
      REMOVE KRWSTROMENDID
      REMOVE VAARWEGID
      REMOVE MEETLOCATIEID
      REMOVE TIJDSTIPREGISTRATIE
      REMOVE OBJECTBEGINTIJD
      REMOVE OBJECTEINDTIJD
      REMOVE LOKAALID
      REMOVE NAMESPACE
      REMOVE DETAILNIVEAUGEOMETRIE
      REMOVE LVPUBLICATIEDATUM
      REMOVE WS_LEGGERPRODUCT
      REMOVE WS_VASTSTELLINGLEGGER
      REMOVE WS_VOLUME
      REMOVE WS_AANLEGJAAR
      REMOVE WS_BERGENDVERMWINTER
      REMOVE WS_BERGENDVERMZOMER
      REMOVE CODEHISTORIE
      REMOVE CREATED_USER
      REMOVE CREATED_DATE
      REMOVE LAST_EDITED_USER
      REMOVE LAST_EDITED_DATE
      REMOVE GLOBALID
      REMOVE WS_VERGUNNINGNUMMER
      SET_TO Ruwheidstypecode = StricklerKs
      SET_TO Ruwheidswaardelaag = 15
      SET_TO Ruwheidswaardehoog = 25
      REMOVE SE_ANNO_CAD_DATA
    -> Tester

Bookmark: 1.2 Controle naam en code
Note: Tester / Volledigheid van de gegevens, test of: / - Code heeft een waarde / - Naam heeft een waarde / Als het beide heeft -> Passed / Zo niet -> Failed
Tester
    BOOL_OP = OR
    TEST_CLAUSE:
      TEST @Value(Code) ATTRIBUTE_HAS_VALUE ""
      TEST @Value(Naam) ATTRIBUTE_HAS_VALUE ""
    PASSED -> AttributeValidator_2
    FAILED -> AttributeManager_28
Note: AttributeValidator / Checkt of de Code uniek is / Is dit het geval -> Passed / Zo niet -> Failed
AttributeValidator_2
    TABLE = Code;ATTRIBUTE_UNIQUE;<Unused>
    PASSED -> Snapper
    FAILED -> AttributeManager_28

Bookmark: 1.3 Verbeterslag - Let op: Bewerking door snapping
Note: Snapper / Sommige waterlopen sluiten niet exact op elkaar aan (er is geen 'snap') / De Snapper sluit de waterlopen op elkaar aan als ze 10 centimer / van elkaar af liggen. / Parameter: segment snapping, 0.1
Snapper
    SNAPTYPE_PARAM = Segment Snapping
    TOLERANCE = 0.1
    SNAPPED -> Snapper_SNAPPED_-__Tester_5
    UNTOUCHED -> Snapper_SNAPPED_-__Tester_5
Snapper_SNAPPED_-__Tester_5: Junction
    -> TopologyBuilder

Bookmark: 1.5 Bewerking 3 - Indexering per Code
Note: TopologyBuilder / Creeert een 'Node' op ieder 'kruispunt' en / knipt de lijnen van de waterlopen op / bij elk knooppunt.
TopologyBuilder
    ALLOW_CYCLES = No
    BOUNDING_EDGES = All
    CLEAN_DATA = No
    DEAGGREGATE_INPUT = Yes
    MAX = 0
    OVERLAPPING_MODE = No
    PROP_ATTRS = No
    LINE -> UUIDGenerator
Note: UUIDGenerator / Maakt een uniek ID aan voor / ieder nieuw stukje lijn (HydroObject)
UUIDGenerator
    UUID_ATTR = UUID
    -> ListBuilder
    -> AttributeManager_3
Note: AttributeManager_6 / Verwijdert de onnodige list attributen
AttributeManager_6
    ATTR_TABLE:
      REMOVE _fme_validation_message
      REMOVE _edge_id
      REMOVE _right_face
      REMOVE _left_face
      REMOVE _right_edge
      REMOVE _left_edge
      REMOVE _from_node
      REMOVE _to_node
      REMOVE _faces
      RENAME_SET_VALUE _element_index > Indexering
    -> FeatureMerger [SUPPLIER]
Note: AttributeManager_3 / Behoudt de Geometry / met als enige attribuut het / unieke ID
AttributeManager_3
    ATTR_TABLE:
      REMOVE _faces
      REMOVE OBJECTID
      REMOVE Code
      REMOVE Administatiefgebiedid
      REMOVE Naam
      REMOVE LeggerStatus
      REMOVE StatusObjectCode
      REMOVE DatumRealisatieObject
      REMOVE DatumStatusObject
      REMOVE Ruwheidstypecode
      REMOVE Ruwheidswaardelaag
      REMOVE Ruwheidswaardehoog
      REMOVE _fme_validation_message
      REMOVE _edge_id
      REMOVE _right_face
      REMOVE _left_face
      REMOVE _right_edge
      REMOVE _left_edge
      REMOVE _from_node
      REMOVE _to_node
    -> FeatureMerger [REQUESTOR]
Note: FeatureMerger / Voegt de geometry (lijn) / samen met de attributen inclusief / de aangemaakte indexering / op basis van het unieke ID
FeatureMerger
    ATTR_ACCUM_MODE = Merge Supplier
    ATTR_CONFLICT_RES = Use Requestor
    IGNORE_NULLS = No
    JOIN_KEYS = @Value(UUID) @Value(UUID) AUTO
    MERGE_TYPE = Attributes and Geometry
    PROCESS_DUPS = No
    REJECT_NULL_MISSING_KEYS = No
    SUPPLIERS_FIRST = No
    MERGED -> AttributeManager

Bookmark: 1.5.1 Bewerking 4
ListBuilder
    GRP_BY = Code
    LIST_NAME = _IDcounter
    -> ListExploder
Note: ListExploder / Met een list wordt er per / Code een lijst gemaakt van / de aanwezige opgeknipte / HydroObjecten onder die code. / Deze worden in een list automatisch / geïndexeerd. Met de exploder worden / er weer afzonderlijke HydroObjecten / van gemaakt, nu inclusief Indexering
ListExploder
    ATTR_ACCUM_MODE = Merge Incoming List
    ATTR_CONFLICT_RES = Use Incoming List
    INDEX_ATTR = _element_index
    LIST_ATTR = _IDcounter{}
    ELEMENTS -> AttributeManager_6

Bookmark: 1.6 Bewerking 5
Note: AttributeManager / Voegt de indexering toe / aan de betreffende Code. / Haalt onnodige attributen weg.
AttributeManager
    ATTR_TABLE:
      SET_TO Code = @Value(Code)_@Value(Indexering)
      REMOVE OBJECTID
      RENAME_SET_VALUE Administatiefgebiedid > administatiefgebied = limburg
      SET_TO Ruwheidstypecode = stricklerks
      SET_TO Ruwheidswaardelaag = 15
      SET_TO Ruwheidswaardehoog = 25
      SET_TO StatusObjectCode = FME_CONDITIONAL:DEFAULT_VALUE'onbekend'BOOL_OP;OR;COMPOSITE_TEST;<Unused>;TEST @Value(StatusObjectCode) = 1'planvorming'BOOL_OP;OR;COMPOSITE_TEST;<Unused>;TEST @Value(StatusObjectCode) = 3'gerealiseerd'BOOL_OP;OR;COMPOSITE_TEST;<Unused>;TEST @Value(StatusObjectCode) = 4'buiten bedrijf'BOOL_OP;OR;COMPOSITE_TEST;<Unused>;TEST @Value(StatusObjectCode) = 5'niet meer aanwezig'BOOL_OP;OR;COMPOSITE_TEST;<Unused>;TEST @Value(StatusObjectCode) = 7'te verwijderen'FME_NUM_CONDITIONS6___
      SET_TO InModel
      REMOVE UUID
      REMOVE Indexering
    -> hydroobject (writer FILEGDB_1)
    -> AttributeManager_23
    -> StatisticsCalculator

Bookmark: 1.7 Controle Attribuutwaardes
Note: Alle testers in deze bookmark testen of het attribuut waar ze op testen (staat er dikgedrukt boven) een waarde heeft. Wanneer dit niet het geval is dan krijgt het attribuut 'MissendeWaardes' een waarde van +1.
AttributeManager_23
    ATTR_TABLE = SET_TO MissendeWaardes = 0
    -> Tester_StatusObjectCode
Note: Tester_StatusObjectCode
Tester_StatusObjectCode
    BOOL_OP = OR
    TEST_CLAUSE = TEST @Value(StatusObjectCode) ATTRIBUTE_HAS_VALUE ""
    PASSED -> Tester_DatumStatusObject
    FAILED -> AttributeManager_24
AttributeManager_24
    ATTR_TABLE = SET_TO MissendeWaardes = @add(@Value(MissendeWaardes),1)
    -> Tester_DatumStatusObject
Note: Tester_DatumStatusObject
Tester_DatumStatusObject
    BOOL_OP = OR
    TEST_CLAUSE = TEST @Value(DatumStatusObject) ATTRIBUTE_HAS_VALUE ""
    PASSED -> Tester_DatumRealisatieObject
    FAILED -> AttributeManager_25
AttributeManager_25
    ATTR_TABLE = SET_TO MissendeWaardes = @add(@Value(MissendeWaardes),1)
    -> Tester_DatumRealisatieObject
Note: Tester_DatumRealisatieObject
Tester_DatumRealisatieObject
    BOOL_OP = OR
    TEST_CLAUSE = TEST @Value(DatumRealisatieObject) ATTRIBUTE_HAS_VALUE ""
    PASSED -> Tester_Leggerstatus
    FAILED -> AttributeManager_26
AttributeManager_26
    ATTR_TABLE = SET_TO MissendeWaardes = @add(@Value(MissendeWaardes),1)
    -> Tester_Leggerstatus
Note: Tester_Leggerstatus
Tester_Leggerstatus
    BOOL_OP = OR
    TEST_CLAUSE = TEST @Value(LeggerStatus) ATTRIBUTE_HAS_VALUE ""
    PASSED -> AttributeManager_28
    FAILED -> AttributeManager_27
AttributeManager_27
    ATTR_TABLE = SET_TO MissendeWaardes = @add(@Value(MissendeWaardes),1)
    -> AttributeManager_28
Note: AttributeManager_28 / verwijderen onnodige attributen
AttributeManager_28
    ATTR_TABLE:
      REMOVE _fme_validation_message_list{}
      REMOVE _fme_validation_message
    -> HYDROOBJECT_MissendeWaardes (writer FILEGDB_2)

Bookmark: 1.8.1 Output naar FileGDB 'HDBterugkoppelingDAMO'
Note: HYDROOBJECT_MissendeWaardes: TerugkoppelingDAMO [FILEGDB] - 5 / Schrijft alle HydroObjecten weg in een File Geodatabase als een / Polyline. Dit inclusief het attribuut 'MissendeWaardes' waarin is aangegeven / hoeveel attributen vanuit DAMO geen waarde hebben.
HYDROOBJECT_MissendeWaardes (writer FILEGDB_2)
    attributes: Code text(75), Administatiefgebiedid text(75), Ruwheidstypecode text(75), Ruwheidswaardelaag text(75), Ruwheidswaardehoog text(75), Naam text(75), StatusObjectCode text(75), DatumStatusObject text(75), DatumRealisatieObject text(75), LeggerStatus text(75), InModel text(75), MissendeWaardes text(75)

Bookmark: 1. HydroObject
StatisticsCalculator
    COMPUTE_HISTOGRAM = NO
    COUNT_ATTR = _count
    GROUP_BY = StatusObjectCode
    PREPEND_ATTR_NAME_CHOICE = For multiple results only
    STATS_ATTRS = StatusObjectCode
    SUMMARY -> StatisticsCalculator_Summary
StatisticsCalculator_Summary: Inspector

Bookmark: 1.8.2 Output naar FileGDB 'HDB'
Note: DAMO_W_HYDROOBJECT: HydrologischeDatabase [FILEGDB] - 2 / Schrijft de HydroObjecten weg in een File Geodatabase als een / Polyline.
hydroobject (writer FILEGDB_1)
    attributes: code text(75), administatiefgebied text(75), ruwheidstypecode text(75), ruwheidswaardelaag text(75), ruwheidswaardehoog text(75), statusobjectcode text(75), naam text(200)
