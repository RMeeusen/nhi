FME workspace 03_HyDAMO_Stuw.fmw

Parameters:
- DestDataset_FILEGDB_22 = N:\HDB\Data\HDBTerugkoppelingDAMO.gdb   # Destination Geodatabase
- SourceDataset_ORACLE_SPATIAL_9 = wsl-ora30.wsl.lan\damo   # Service Name or Easy Connect
- DestDataset_FILEGDB_24 = \\wsl-app09\Sobek\HDB\Data\HDB.gdb   # Destination Geodatabase

Readers:
- ORACLE_SPATIAL_1: ORACLE_SPATIAL from $(SourceDataset_ORACLE_SPATIAL_9) in Netherlands-RDNew-2008

Writers:
- FILEGDB_1: FILEGDB to $(DestDataset_FILEGDB_22)
- FILEGDB_2: FILEGDB to $(DestDataset_FILEGDB_24)

Note: DAMO_W.STUW: damo [ORACLE_SPATIAL] / Import vanuit DAMO
STUW (reader ORACLE_SPATIAL_1)
    attributes: OBJECTID number(38,0), SE_ANNO_CAD_DATA blob, CODE nvarchar(50), NAAM nvarchar(100), STATUSLEGGERWATERSYSTEEM number(5,0), STATUSLEGGERWATERVEILIGHEID number(5,0), STATUSOBJECT number(5,0), HYPERLINK nvarchar(100), OPMERKING nvarchar(250), TYPEWATERKERENDECONSTRUCTIE number(5,0), INDICATIEWATERKEREND number(5,0), CATEGORIE number(5,0), KERENDEHOOGTE number(8,2), SOORTSTUW number(3,0), DOORSTROOMBREEDTE number(8,2), KRUINBREEDTE number(8,2), DREMPELPEIL number(8,2), LAAGSTEDOORSTROOMHOOGTE number(8,2), HOOGSTEDOORSTROOMHOOGTE number(8,2), SIGNALERINGSPEIL number(8,2), SLUITPEIL number(8,2), SOORTREGELBAARHEID number(3,0), HOOGTECONSTRUCTIE number(8,2), OPENKEERPEIL number(8,2), OPENINGSPEIL number(8,2), RICHTING number(5,2), REGENWATERBUFFERCOMPARTIMENTID number(10,0), SOORTMATERIAAL number(3,0), WATERKERINGID number(10,0), METADATAID number(10,0),
      TIJDSTIPREGISTRATIE date, OBJECTBEGINTIJD date, OBJECTEINDTIJD date, LOKAALID nvarchar(50), NAMESPACE nvarchar(50), DETAILNIVEAUGEOMETRIE number(10,0), LVPUBLICATIEDATUM date, WS_AANLEGJAAR nvarchar(4), WS_BODEMVERDEDIGING nvarchar(12), WS_CALAMITEITENOBJECT nvarchar(1), WS_VPO_IDNR number(10,0), WS_LEGGERPRODUCT nvarchar(10), WS_VASTSTELLINGLEGGER date, WS_KRUINVORM number(2,0), WS_MINIMALEKRUINHOOGTE number(6,3), WS_FASETEKST nvarchar(200), WS_FASEOPM nvarchar(250), WS_FASE4 number(6,2), WS_FASE3 number(6,2), WS_FASE2 number(6,2), WS_FASE1 number(6,2), WS_FASE0 number(6,2), WS_DREMPELHOOGTE number(6,2), WS_DREMPELBREEDTE number(4,2), WS_CONSTRUCTIELENGTE number(4,2), WS_CODEBHR nvarchar(25), WS_BOERENSTUW nvarchar(10), WS_VASTSTUWPEIL number(6,3), WS_PLAATSELIJKEAANDUIDING nvarchar(50), CODEHISTORIE nvarchar(50),
      CREATED_USER nvarchar(255), CREATED_DATE date, LAST_EDITED_USER nvarchar(255), LAST_EDITED_DATE date, GLOBALID char(38), WS_VERGUNNINGNUMMER nvarchar(50)
    -> Tester_4
Note: DAMO_W.HYDROOBJECT: damo [ORACLE_SPATIAL] / Import vanuit DAMO, ook wel Waterlopen genoemd
HYDROOBJECT (reader ORACLE_SPATIAL_1)
    attributes: OBJECTID number(38,0), SE_ANNO_CAD_DATA blob, CODE nvarchar(50), NAAM nvarchar(100), STATUSLEGGERWATERSYSTEEM number(5,0), STATUSLEGGERWATERVEILIGHEID number(5,0), STATUSOBJECT number(5,0), HYPERLINK nvarchar(100), OPMERKING nvarchar(250), SOORTOPPWATERKWALITEIT number(3,0), SOORTOPPWATERKWANTITEIT number(3,0), CATEGORIEOPPWATERLICHAAM number(3,0), BREEDTE number(8,2), LENGTE number(8,2), DRAINEERT number(10,0), GETIJDEBEINVLOED nvarchar(1), NIVEAU number(3,0), ONTSTAANSWIJZE number(3,0), OPPWATERVOLGNUMMER number(8,0), RUIMTELIJKEAFBAKENINGBEKEND nvarchar(1), PERSISTENTIE number(3,0), OPPERVLAKTEWATERLICHAAMID number(10,0), METADATAID number(10,0), HYDROOBJECTDEELID number(10,0), KRWSTROMENDID number(10,0), VAARWEGID number(10,0), MEETLOCATIEID number(10,0), TIJDSTIPREGISTRATIE date, OBJECTBEGINTIJD date, OBJECTEINDTIJD date,
      LOKAALID nvarchar(50), NAMESPACE nvarchar(50), DETAILNIVEAUGEOMETRIE number(10,0), LVPUBLICATIEDATUM date, WS_LEGGERPRODUCT nvarchar(10), WS_VASTSTELLINGLEGGER date, WS_VOLUME number(12,0), WS_AANLEGJAAR nvarchar(4), WS_BERGENDVERMWINTER number(12,0), WS_BERGENDVERMZOMER number(12,0), CODEHISTORIE nvarchar(50), CREATED_USER nvarchar(255), CREATED_DATE date, LAST_EDITED_USER nvarchar(255), LAST_EDITED_DATE date, GLOBALID char(38), WS_VERGUNNINGNUMMER nvarchar(50)
    -> AttributeRemover

Bookmark: 3.1 Bewerking 1
Note: Tester / Laat alleen stuwen door die geen boerenstuw / zijn. Waarbij geldt: / - WS_Boerenstuw != j -> Passed / - WS_Boerenstuw = j -> Failed
Tester_4
    BOOL_OP = OR
    TEST_CLAUSE = TEST @Value(WS_BOERENSTUW) != j
    PASSED -> AttributeManager_4
Note: AttributeManager / Behoudt alleen de nodige attributen vanuit Input
Note: De volgende attributen / worden toegevoegd / met standaard waarde / - HoogsteDoorstroombreedte (waarde hetzelfde / als LaagsteDoorstroombreedte) / - Afvoercoefficient (waarde 1) / Zonder standaard waarde (leeg!) / - AfsluitmiddelCode / - DoorstroomopeningCode / - NormaalZomerPeil / - NormaalWinterPeil / - Kruinvorm
AttributeManager_4
    ATTR_TABLE:
      RENAME_SET_VALUE CODE > Code
      RENAME_SET_VALUE SOORTREGELBAARHEID > Soortregelbaarheid
      RENAME_SET_VALUE DOORSTROOMBREEDTE > LaagsteDoorstroombreedte
      SET_TO HoogsteDoorstroombreedte = @Value(LaagsteDoorstroombreedte)
      RENAME_SET_VALUE LAAGSTEDOORSTROOMHOOGTE > Laagstedoorstroomhoogte
      RENAME_SET_VALUE HOOGSTEDOORSTROOMHOOGTE > Hoogstedoorstroomhoogte
      RENAME_SET_VALUE SOORTSTUW > SoortStuw
      RENAME_SET_VALUE STATUSOBJECT > StatusObject
      SET_TO Afvoercoefficient = 1
      SET_TO AfsluitmiddelCode
      SET_TO DoorstroomopeningCode
      SET_TO NormaalZomerPeil
      SET_TO NormaalWinterPeil
      SET_TO Kruinvorm
      SET_TO InModel
      REMOVE OBJECTID
      REMOVE SE_ANNO_CAD_DATA
      REMOVE NAAM
      REMOVE STATUSLEGGERWATERSYSTEEM
      REMOVE STATUSLEGGERWATERVEILIGHEID
      REMOVE HYPERLINK
      REMOVE OPMERKING
      REMOVE TYPEWATERKERENDECONSTRUCTIE
      REMOVE INDICATIEWATERKEREND
      REMOVE CATEGORIE
      REMOVE KERENDEHOOGTE
      REMOVE DREMPELPEIL
      REMOVE SIGNALERINGSPEIL
      REMOVE SLUITPEIL
      REMOVE HOOGTECONSTRUCTIE
      REMOVE OPENKEERPEIL
      REMOVE OPENINGSPEIL
      REMOVE RICHTING
      REMOVE REGENWATERBUFFERCOMPARTIMENTID
      REMOVE SOORTMATERIAAL
      REMOVE WATERKERINGID
      REMOVE METADATAID
      REMOVE TIJDSTIPREGISTRATIE
      REMOVE OBJECTBEGINTIJD
      REMOVE OBJECTEINDTIJD
      REMOVE LOKAALID
      REMOVE NAMESPACE
      REMOVE DETAILNIVEAUGEOMETRIE
      REMOVE LVPUBLICATIEDATUM
      REMOVE WS_AANLEGJAAR
      REMOVE WS_BODEMVERDEDIGING
      REMOVE WS_CALAMITEITENOBJECT
      REMOVE WS_VPO_IDNR
      REMOVE WS_LEGGERPRODUCT
      REMOVE WS_VASTSTELLINGLEGGER
      REMOVE WS_KRUINVORM
      REMOVE WS_MINIMALEKRUINHOOGTE
      REMOVE WS_FASETEKST
      REMOVE WS_FASEOPM
      REMOVE WS_FASE4
      REMOVE WS_FASE3
      REMOVE WS_FASE2
      REMOVE WS_FASE1
      REMOVE WS_FASE0
      REMOVE WS_DREMPELHOOGTE
      REMOVE WS_DREMPELBREEDTE
      REMOVE WS_CONSTRUCTIELENGTE
      REMOVE WS_CODEBHR
      REMOVE WS_BOERENSTUW
      REMOVE WS_VASTSTUWPEIL
      REMOVE WS_PLAATSELIJKEAANDUIDING
      REMOVE CODEHISTORIE
      REMOVE CREATED_USER
      REMOVE CREATED_DATE
      REMOVE LAST_EDITED_USER
      REMOVE LAST_EDITED_DATE
      REMOVE GLOBALID
      REMOVE WS_VERGUNNINGNUMMER
    -> Tester_13

Bookmark: 3.1.1. Bewerking StatusObject
Note: Tester_13 / Test of het attribuut 'StatusObject / een waarde heeft
Tester_13
    BOOL_OP = OR
    TEST_CLAUSE = TEST @Value(StatusObject) ATTRIBUTE_HAS_VALUE ""
    PASSED -> Tester_13_PASSED_-__Tester_2
    FAILED -> AttributeManager_47
Note: AttributeManager_47 / Wanneer 'StatusObject' / geen waarde heeft wordt hier de / waarde 98 aan gegeven (code / voor missende waarde)
AttributeManager_47
    ATTR_TABLE = SET_TO StatusObject = 98
    -> Tester_13_PASSED_-__Tester_2
Tester_13_PASSED_-__Tester_2: Junction
    -> Tester_2

Bookmark: 3.2 Controle naam
Note: Tester / Volledigheid van de gegevens, test of: / - Code heeft een waarde / Als het dit heeft -> Passed / Zo niet -> Failed
Tester_2
    BOOL_OP = OR
    TEST_CLAUSE = TEST @Value(Code) ATTRIBUTE_HAS_VALUE ""
    PASSED -> AttributeValidator
    FAILED -> AttributeManager_20
Note: AttributeValidator / Checkt of de Code uniek is / Is dit het geval -> Passed / Zo niet -> Failed
AttributeValidator
    TABLE = Code;ATTRIBUTE_UNIQUE;<Unused>
    PASSED -> PointOnLineOverlayer [POINT]
    FAILED -> AttributeManager_20

Bookmark: 3.3.1 Bewerking
Note: AttributeRemover / Verwijdert alle attributen van de HydroObjecten / zodat deze niet worden meegenomen in de / Controle
AttributeRemover
    REMOVE_ATTRS = SOORTOPPWATERKWANTITEIT,WS_BERGENDVERMZOMER,GLOBALID,LENGTE,BREEDTE,OBJECTEINDTIJD,NIVEAU,METADATAID,ONTSTAANSWIJZE,STATUSLEGGERWATERVEILIGHEID,VAARWEGID,LAST_EDITED_USER,WS_VASTSTELLINGLEGGER,LVPUBLICATIEDATUM,DETAILNIVEAUGEOMETRIE,OBJECTBEGINTIJD,OBJECTID,WS_VERGUNNINGNUMMER,KRWSTROMENDID,OPPWATERVOLGNUMMER,PERSISTENTIE,HYDROOBJECTDEELID,RUIMTELIJKEAFBAKENINGBEKEND,WS_BERGENDVERMWINTER,CREATED_USER,GETIJDEBEINVLOED,STATUSOBJECT,WS_VOLUME,LOKAALID,CREATED_DATE,NAMESPACE,CODE,DRAINEERT,CODEHISTORIE,CATEGORIEOPPWATERLICHAAM,OPMERKING,TIJDSTIPREGISTRATIE,STATUSLEGGERWATERSYSTEEM,LAST_EDITED_DATE,NAAM,OPPERVLAKTEWATERLICHAAMID,WS_AANLEGJAAR,SOORTOPPWATERKWALITEIT,HYPERLINK,MEETLOCATIEID,WS_LEGGERPRODUCT,SE_ANNO_CAD_DATA
    -> PointOnLineOverlayer [LINE]

Bookmark: 3.3 Controle Stuw ligt op een HydroObject
Note: PointOnLineOverlayer / Kijkt of de Stuwen (punten) op een / lHydroObject (lijn) staan, met een marge van / 10 centimeter / Als dit zo is krijgt het attribuut 'Overlap' een waarde van / 1 of meer (als een stuw op één of meerdere lijnen ligt)
PointOnLineOverlayer
    ATTR_ACCUM_MODE = Merge Incoming
    ATTR_CONFLICT_RES = Use Original
    OV_ATTR = Overlap
    TOLERANCE = 0.1
    POINT -> AttributeManager_5

Bookmark: 3.4 Bewerking 2
Note: AttributeManager / Behoudt alleen de nodige attributen / Voegt de volgende attributen toe: / - Inmodel
AttributeManager_5
    ATTR_TABLE = REMOVE _fme_validation_message
    -> Tester_3
    -> AttributeManager_16

Bookmark: 3.6 Controle missende waardes
AttributeManager_16
    ATTR_TABLE = SET_TO MissendeWaardes = 0
    -> Tester_Soortregelbaarheid
Note: Tester_Soortregelbaarheid
Tester_Soortregelbaarheid
    BOOL_OP = AND
    TEST_CLAUSE = TEST @Value(Soortregelbaarheid) ATTRIBUTE_HAS_VALUE ""
    PASSED -> Tester_Laagstedoorstroombreedte
    FAILED -> AttributeManager_21
AttributeManager_21
    ATTR_TABLE = SET_TO MissendeWaardes = @add(@Value(MissendeWaardes),1)
    -> Tester_Laagstedoorstroombreedte
Note: Tester_Laagstedoorstroombreedte
Tester_Laagstedoorstroombreedte
    BOOL_OP = OR
    TEST_CLAUSE = TEST @Value(LaagsteDoorstroombreedte) ATTRIBUTE_HAS_VALUE ""
    PASSED -> Tester_HoogsteDoorstroombreedte
    FAILED -> AttributeManager_14
AttributeManager_14
    ATTR_TABLE = SET_TO MissendeWaardes = @add(@Value(MissendeWaardes),1)
    -> Tester_HoogsteDoorstroombreedte
Note: Alle testers in deze bookmark testen of het attribuut waar ze op testen (staat er dikgedrukt boven) een waarde heeft. Wanneer dit niet het geval is dan krijgt het attribuut 'MissendeWaardes' een waarde van +1.
Note: Tester_HoogsteDoorstroombreedte
Tester_HoogsteDoorstroombreedte
    BOOL_OP = OR
    TEST_CLAUSE = TEST @Value(HoogsteDoorstroombreedte) ATTRIBUTE_HAS_VALUE ""
    PASSED -> Tester_Laagstedoorstroomhoogte
    FAILED -> AttributeManager_15
AttributeManager_15
    ATTR_TABLE = SET_TO MissendeWaardes = @add(@Value(MissendeWaardes),1)
    -> Tester_Laagstedoorstroomhoogte
Note: Tester_Laagstedoorstroomhoogte
Tester_Laagstedoorstroomhoogte
    BOOL_OP = OR
    TEST_CLAUSE = TEST @Value(Laagstedoorstroomhoogte) ATTRIBUTE_HAS_VALUE ""
    PASSED -> Tester_Hoogstedoorstroomhoogte
    FAILED -> AttributeManager_17
AttributeManager_17
    ATTR_TABLE = SET_TO MissendeWaardes = @add(@Value(MissendeWaardes),1)
    -> Tester_Hoogstedoorstroomhoogte
Note: Tester_Hoogstedoorstroomhoogte
Tester_Hoogstedoorstroomhoogte
    BOOL_OP = OR
    TEST_CLAUSE = TEST @Value(Hoogstedoorstroomhoogte) ATTRIBUTE_HAS_VALUE ""
    PASSED -> Tester_SoortStuw
    FAILED -> AttributeManager_18
AttributeManager_18
    ATTR_TABLE = SET_TO MissendeWaardes = @add(@Value(MissendeWaardes),1)
    -> Tester_SoortStuw
Note: Tester_SoortStuw
Tester_SoortStuw
    BOOL_OP = OR
    TEST_CLAUSE = TEST @Value(SoortStuw) ATTRIBUTE_HAS_VALUE ""
    PASSED -> Tester_StatusObject
    FAILED -> AttributeManager_19
AttributeManager_19
    ATTR_TABLE = SET_TO MissendeWaardes = @add(@Value(MissendeWaardes),1)
    -> Tester_StatusObject
Note: Tester_StatusObject
Tester_StatusObject
    BOOL_OP = OR
    TEST_CLAUSE = TEST @Value(StatusObject) ATTRIBUTE_HAS_VALUE ""
    PASSED -> AttributeManager_20
    FAILED -> AttributeManager_22
AttributeManager_22
    ATTR_TABLE = SET_TO MissendeWaardes = @add(@Value(MissendeWaardes),1)
    -> AttributeManager_20
AttributeManager_20
    ATTR_TABLE:
      REMOVE Overlap
      REMOVE _fme_validation_message_list{}
      REMOVE _fme_validation_message
    -> STUW_MissendeWaardes (writer FILEGDB_1)

Bookmark: 3.8.1 Output naar FileGDB TerugkoppelingDAMO
Note: STUW_MissendeWaardes: TerugkoppelingDAMO [FILEGDB] - 3 / Schrijft alle Stuwen weg in een File Geodatabase als punten. / Dit inclusief het attribuut 'MissendeWaardes' waarin is aangegeven / hoeveel attributen vanuit DAMO geen waarde hebben.
STUW_MissendeWaardes (writer FILEGDB_1)
    attributes: Code text(75), Soortregelbaarheid text(75), LaagsteDoorstroombreedte text(75), HoogsteDoorstroombreedte text(75), Laagstedoorstroomhoogte text(75), Hoogstedoorstroomhoogte text(75), Afvoercoefficient text(75), SoortStuw text(75), StatusObject text(75), AfsluitmiddelCode text(75), DoorstroomopeningCode text(75), NormaalZomerPeil text(75), NormaalWinterpeil text(75), Kruinvorm text(75), InModel text(75), MissendeWaardes text(75)
Note: STUW_BuitenHydroObject: HDB [FILEGDB] / Schrijft alle Stuwen weg in een File Geodatabase die / niet binnen 10 centimeter van een HydroObject liggen.
STUW_BuitenHydroObject (writer FILEGDB_1)
    attributes: Code text(75), Soortregelbaarheid text(75), LaagsteDoorstroombreedte text(75), HoogsteDoorstroombreedte text(75), Laagstedoorstroomhoogte text(75), Hoogstedoorstroomhoogte text(75), Afvoercoefficient text(75), SoortStuw text(75), StatusObject text(75), AfsluitmiddelCode text(75), DoorstroomopeningCode text(75), NormaalZomerPeil text(75), NormaalWinterPeil text(75), Kruinvorm text(75), InModel text(75), Overlap text(75)

Bookmark: 3.5 Controle Overlap met HydroObject
Note: Tester / Test of de waarde Overlap groter of gelijk / aan 1 is. / Is dit zo (stuw ligt op een HydroObject) -> Passed / Is dit niet zo (stuw ligt niet binnen 1 / meter van een HydroObject) -> Failed
Tester_3
    BOOL_OP = OR
    TEST_CLAUSE = TEST @Value(Overlap) >= 1
    PASSED -> AttributeManager_49
    FAILED -> SpatialFilter_2 [Candidate]

Bookmark: 3.7 Bewerking Code Stuwen
Note: AttributeManager_49 / voegt bij stuwen S_ toe voor de code
AttributeManager_49
    ATTR_TABLE:
      SET_TO Code = S_@Value(Code)
      REMOVE Overlap
    -> AttributeManager_45_OUTPUT_-__STUW
AttributeManager_45
    ATTR_TABLE:
      SET_TO Code = S_B_@Value(Code)
      REMOVE _predicate
      REMOVE Overlap
    -> AttributeManager_45_OUTPUT_-__STUW
AttributeManager_45_OUTPUT_-__STUW: Junction
    -> AttributeManager

Bookmark: Extra import data
Note: DAMO_W.REGENWATERBUFFERCOMPARTIMENT: damo [ORACLE_SPATIAL] / Import van regenwaterbuffercompartimenten vanuit DAMO ten behoeve van / een ruimtelijke overlay met de stuwen
REGENWATERBUFFERCOMPARTIMENT (reader ORACLE_SPATIAL_1)
    attributes: OBJECTID number(38,0), SE_ANNO_CAD_DATA blob, CODE nvarchar(50), NAAM nvarchar(100), STATUSLEGGERWATERSYSTEEM number(5,0), STATUSLEGGERWATERVEILIGHEID number(5,0), STATUSOBJECT number(5,0), HYPERLINK nvarchar(100), OPMERKING nvarchar(250), VOLUMECOMPARTIMENT number(38,8), OPPERVLAKTECOMPARTIMENT number(38,8), REGENWATERBUFFERID number(10,0), TIJDSTIPREGISTRATIE date, OBJECTBEGINTIJD date, OBJECTEINDTIJD date, LOKAALID nvarchar(50), NAMESPACE nvarchar(50), DETAILNIVEAUGEOMETRIE number(10,0), LVPUBLICATIEDATUM date, WS_COMPARTIMENT number(3,0), WS_VASTSTELLINGLEGGER date, WS_AANLEGDATUM date, WS_LEGGERPRODUCT nvarchar(10), WS_KOPPEL nvarchar(50), CODEHISTORIE nvarchar(50), WS_METADATAID number(10,0), CREATED_USER nvarchar(255), CREATED_DATE date, LAST_EDITED_USER nvarchar(255), LAST_EDITED_DATE date,
      GLOBALID char(38)
    -> AttributeManager_48
AttributeManager_48
    ATTR_TABLE:
      REMOVE SE_ANNO_CAD_DATA
      REMOVE CODE
      REMOVE NAAM
      REMOVE STATUSLEGGERWATERSYSTEEM
      REMOVE STATUSLEGGERWATERVEILIGHEID
      REMOVE STATUSOBJECT
      REMOVE HYPERLINK
      REMOVE OPMERKING
      REMOVE VOLUMECOMPARTIMENT
      REMOVE OPPERVLAKTECOMPARTIMENT
      REMOVE REGENWATERBUFFERID
      REMOVE TIJDSTIPREGISTRATIE
      REMOVE OBJECTBEGINTIJD
      REMOVE OBJECTEINDTIJD
      REMOVE LOKAALID
      REMOVE NAMESPACE
      REMOVE DETAILNIVEAUGEOMETRIE
      REMOVE LVPUBLICATIEDATUM
      REMOVE WS_COMPARTIMENT
      REMOVE WS_VASTSTELLINGLEGGER
      REMOVE WS_AANLEGDATUM
      REMOVE WS_LEGGERPRODUCT
      REMOVE WS_KOPPEL
      REMOVE CODEHISTORIE
      REMOVE WS_METADATAID
      REMOVE CREATED_USER
      REMOVE CREATED_DATE
      REMOVE LAST_EDITED_USER
      REMOVE LAST_EDITED_DATE
      REMOVE GLOBALID
    -> SpatialFilter_2 [Filter]

Bookmark: 3.6 Controle overlap met RegenwaterBuffer
Note: SpatialFilter_2 / Test of de Stuw enige vorm van / overlap (intersect) heeft met een / Regenwaterbuffercompartiment
Note: AttributeManager_45 / voegt bij stuwen met een buffer overlap / S_B_ toe voor de code
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager_45
    FAILED -> STUW_BuitenHydroObject (writer FILEGDB_1)

Bookmark: 3. Stuw
AttributeManager
    ATTR_TABLE:
      SET_TO Soortregelbaarheid = FME_CONDITIONAL:DEFAULT_VALUE'overig'BOOL_OP;OR;COMPOSITE_TEST;<Unused>;TEST @Value(Soortregelbaarheid) = 1'niet regelbaar (vast)'BOOL_OP;OR;COMPOSITE_TEST;<Unused>;TEST @Value(Soortregelbaarheid) = 2'regelbaar, niet automatisch'BOOL_OP;OR;COMPOSITE_TEST;<Unused>;TEST @Value(Soortregelbaarheid) = 3'regelbaar, automatisch'BOOL_OP;OR;COMPOSITE_TEST;<Unused>;TEST @Value(Soortregelbaarheid) = 4'handmatig'FME_NUM_CONDITIONS5___
      SET_TO SoortStuw = FME_CONDITIONAL:DEFAULT_VALUE'onbekend'BOOL_OP;OR;COMPOSITE_TEST;<Unused>;TEST @Value(SoortStuw) = 1'schotbalkstuw'BOOL_OP;OR;COMPOSITE_TEST;<Unused>;TEST @Value(SoortStuw) = 2'stuw met schuif'BOOL_OP;OR;COMPOSITE_TEST;<Unused>;TEST @Value(SoortStuw) = 3'stuw met klep'BOOL_OP;OR;COMPOSITE_TEST;<Unused>;TEST @Value(SoortStuw) = 4'segmentstuw'BOOL_OP;OR;COMPOSITE_TEST;<Unused>;TEST @Value(SoortStuw) = 5'cascadestuw'BOOL_OP;OR;COMPOSITE_TEST;<Unused>;TEST @Value(SoortStuw) = 6'hevelstuw'BOOL_OP;OR;COMPOSITE_TEST;<Unused>;TEST @Value(SoortStuw) = 7'meetstuw'BOOL_OP;OR;COMPOSITE_TEST;<Unused>;TEST @Value(SoortStuw) = 8'meetschot'BOOL_OP;OR;COMPOSITE_TEST;<Unused>;TEST @Value(SoortStuw) = 9'stuw met contra-gewicht'BOOL_OP;OR;COMPOSITE_TEST;<Unused>;TEST @Value(SoortStuw) = 10'inlaat- en/of aflaatstuw'BOOL_OP;OR;COMPOSITE_TEST;<Unused>;TEST @Value(SoortStuw) = 11'overlaat'BOOL_OP;OR;COMPOSITE_TEST;<Unused>;TEST @Value(SoortStuw) = 12'drijverstuw'BOOL_OP;OR;COMPOSITE_TEST;<Unused>;TEST @Value(SoortStuw) = 13'trommelstuw'BOOL_OP;OR;COMPOSITE_TEST;<Unused>;TEST @Value(SoortStuw) = 20'gronddamstuw'BOOL_OP;OR;COMPOSITE_TEST;<Unused>;TEST @Value(SoortStuw) = 21'stuwbalk'BOOL_OP;OR;COMPOSITE_TEST;<Unused>;TEST @Value(SoortStuw) = 22'tuimel- of kantelstuw'BOOL_OP;OR;COMPOSITE_TEST;<Unused>;TEST @Value(SoortStuw) = 23'balgstuw'BOOL_OP;OR;COMPOSITE_TEST;<Unused>;TEST @Value(SoortStuw) = 24'brievenbusstuw'BOOL_OP;OR;COMPOSITE_TEST;<Unused>;TEST @Value(SoortStuw) = 25'knijpstuw'BOOL_OP;OR;COMPOSITE_TEST;<Unused>;TEST @Value(SoortStuw) = 26'conserveringstuw'FME_NUM_CONDITIONS21___
      SET_TO StatusObject = FME_CONDITIONAL:DEFAULT_VALUE'onbekend'BOOL_OP;OR;COMPOSITE_TEST;<Unused>;TEST @Value(StatusObject) = 1'planvorming'BOOL_OP;OR;COMPOSITE_TEST;<Unused>;TEST @Value(StatusObject) = 3'gerealiseerd'BOOL_OP;OR;COMPOSITE_TEST;<Unused>;TEST @Value(StatusObject) = 4'buiten bedrijf'BOOL_OP;OR;COMPOSITE_TEST;<Unused>;TEST @Value(StatusObject) = 5'niet meer aanwezig'BOOL_OP;OR;COMPOSITE_TEST;<Unused>;TEST @Value(StatusObject) = 7'te verwijderen'FME_NUM_CONDITIONS6___
      SET_TO administratiefgebied = limburg
    -> stuw (writer FILEGDB_2)

Bookmark: 3.8.2 Output naar FileGDB HydrologischeDatabase
Note: DAMO_W_STUW: HydrologischeDatabase [FILEGDB] - 2 / Schrijft de Stuwen weg in een File Geodatabase als punten. / (alleen de stuwen binnen 10cm van een HydroObject
stuw (writer FILEGDB_2)
    attributes: code text(75), soortregelbaarheidcode text(75), laagstedoorstroombreedte text(75), hoogstedoorstroombreedte text(75), laagstedoorstroomhoogte text(75), hoogstedoorstroomhoogte text(75), afvoercoefficient text(75), soortstuwcode text(75), statusobjectcode text(75), kruinbreedte text(75), administratiefgebied text(75)
