FME workspace 02B_HyDAMO_DwarsprofielPuntenInterpolatie.fmw

Parameters:
- SourceDataset_FILEGDB = \\wsl-app09\Sobek\HDB\Data\HDB.gdb   # Source Geodatabase
- SourceDataset_FILEGDB_4 = \\wsl-fs01\QdriveWPM\WSL\fileshare\ArcGIS_Brondata\Overige_WPM_Data\OverigeWROData.gdb   # Source Geodatabase
- SourceDataset_ORACLE_SPATIAL = wsl-ora30.wsl.lan/damo   # Service Name or Easy Connect
- DestDataset_FILEGDB = \\wsl-app09\Sobek\HDB\Data\HDB.gdb   # Destination Geodatabase

Readers:
- ORACLE_SPATIAL_1: ORACLE_SPATIAL from $(SourceDataset_ORACLE_SPATIAL) in Netherlands-RDNew-2008
- FILEGDB_1: FILEGDB from $(SourceDataset_FILEGDB)
- FILEGDB_2: FILEGDB from $(SourceDataset_FILEGDB_4)

Writers:
- FILEGDB_3: FILEGDB to $(DestDataset_FILEGDB)

WS_LANDMEETGEGEVENS (reader ORACLE_SPATIAL_1)
    attributes: OBJECTID number(38,0), WS_CODE nvarchar(24), WS_VERVALDATUM date, WS_SOORTLANDMEETLIJN nvarchar(60), WS_BRON nvarchar(50), WS_OPMERKING nvarchar(60), WS_INWINNINGSDATUM date, SE_ANNO_CAD_DATA blob, CODEHISTORIE nvarchar(24), CREATED_USER nvarchar(255), CREATED_DATE date, LAST_EDITED_USER nvarchar(255), LAST_EDITED_DATE date
    -> Tester_2
HYDROOBJECT (reader FILEGDB_1)
    attributes: Code text(75), Administatiefgebiedid text(75), Ruwheidstypecode text(75), Ruwheidswaardelaag text(75), Ruwheidswaardehoog text(75), Naam text(75), StatusObjectCode text(75), DatumStatusObject text(75), DatumRealisatieObject text(75), LeggerStatus text(75), InModel text(75), OBJECTID objectid
    -> Clipper [CLIPPEE]
    -> HYDROOBJECT
Note: Input Dwarsprofiel op bais van / DwarsprofielLocatie-punten / ten behoeve van buffer
Note: Input Dwarsprofiel op bais van / DwarsprofielLocatie-punten / ten behoeve van overlap
HYDROOBJECT: Inspector
DWARSPROFIELLOCATIES (reader FILEGDB_1)
    attributes: Code text(75), HyOb_Code text(200), HyOb_Naam text(200), OBJECTID_1 objectid
    -> CoordinateExtractor
    -> NeighborFinder [CANDIDATE]
GW_PRO (reader FILEGDB_2)
    attributes: PRO_ID objectid, PRO_TYPE text(24), MPN_MPN_ID int, IPRKS_IPRKS_ID int, PROIDENT text(24), OVK_OVK_ID int, DWK_DWK_ID int, OWA_OWA_ID int, PRO_PRO_ID int, PRW_PRW_ID int, DDPKRUIN double, DGPNUMME text(24), OPRRICHT text(13), LBISTATG text(32), DDPHWMAT single, PROSOORT text(30), DDPHWGEM single, OPRDATOP date, DDPZMRPL single, GEGBRON text(50), DDPWNTPL single, OSMOMSCH text(60), DDPOPGPL single, IWS_LEGRT text(0), DDPZETT single, TBTVWIND single, KTCSOORT text(8), DDPRRGLF single, DDPPARAP text(8), DDPITOGT single,
      DDPITOTO single, DDPTOORD text(13), DDPITEEN text(8), DDPIABKL text(8), IWS_X_OFFSET double, IWS_Y_OFFSET double, IWS_VOOR_LEN double, IWS_NA_LEN double, IWS_HYPERLINK text(240), RICHTING single, IWS_GEPEILD_DOOR text(100), IWS_DATUM_GEPEILD date, SE_ANNO_CAD_DATA blob, GEOMETRIE_Length double
    -> Tester_7
Note: AttributeCreator_2 / Creeer attribuut AfstandHydroObject / waarbij de linkerafstand negatief wordt opgenomen / en de rechterafstand positief
AttributeCreator_2
    ATTR_TABLE = SET_TO AfstandHydroObject = FME_CONDITIONAL:DEFAULT_VALUE'@Value(AfstandRechts)'BOOL_OP;OR;COMPOSITE_TEST;<Unused>;TEST @Value(HydroObjectZijde) = Links'@mult(-1,@Value(AfstandLinks))'FME_NUM_CONDITIONS2___
    -> AttributeManager_6
dwarsprofielpunten_interpolatie (writer FILEGDB_3)
    attributes: code text(75), codevolgnummer int, profielcode text(200), administratiefgebied text(75), ruwheidstypecode text(75), ruwheidswaardelaag text(75), ruwheidswaardehoog text(75), statusobjectcode text(75), typeprofielcode text(75)

Bookmark: Selectie zonder vervaldatum, Lengteprofiel en Taludlijn
Note: Tester_2 / Test of de Vervaldatum leeg is / en of daarmee de meetgegevens / niet al vervallen zijn
Tester_2
    BOOL_OP = OR
    TEST_CLAUSE = TEST @Value(WS_VERVALDATUM) = ""
    PASSED -> Tester_3
Note: Tester_3 / Test of de soort landmeetlijn / geen Taludlijn is, deze worden niet / meegenomen
Tester_3
    BOOL_OP = OR
    TEST_CLAUSE = TEST @Value(WS_SOORTLANDMEETLIJN) != Taludlijn
    PASSED -> Tester_6
Note: Tester_6 / Test of de soort landmeetlijn / een Dwarsprofiel is.
Tester_6
    BOOL_OP = OR
    TEST_CLAUSE = TEST @Value(WS_SOORTLANDMEETLIJN) != Dwarsprofiel oppervlaktewater
    PASSED -> Counter_2

Bookmark: Maak Lijn voor DwarsprofielLijn
  Voorwerk om per dwarsprofielpunt een korte lijn te creeeren om de richting van het HydroObject te bepalen
Note: CoordinateExtractor / Bepaal per punt het x en y coordintaat / (benodigd in de Rotator)
CoordinateExtractor
    IND = 0
    MODE = Specify Coordinate
    X_ATTR = x
    Y_ATTR = y
    Z_ATTR = _z
    -> Bufferer
Note: Bufferer / Plaatst een buffer van 0.1 meter / rondom het dwarsprofielpunt
Bufferer
    CAP_STYLE = Square
    INTERP_SEGMENTS = 8
    OFFSET = 0.1
    BUFFERED -> Clipper [CLIPPER]
Note: Clipper / Clipt de lijn die binnen de buffer valt / naar een lijn per dwarsprofielLocatie
Clipper
    ATTR_ACCUM_MODE = Merge Clipper
    ATTR_CONFLICT_RES = Use Clippee
    BOUNDARY_CASES = Treat as Inside
    CLIPPED_ATTR = _clipped
    CLIP_TYPE = Multiple Clippers
    CONNECT_Z_MODE = First Wins
    CREATE_AGGREGATES = Yes
    LINES_AS_SEGMENTS = No
    PRESERVE_CLIPPEE_EXTENTS = No
    INSIDE -> Rotator

Bookmark: Draai en Verleng de lijn
  Draai de lijn die in bewerking 1 is gemaakt 90 graden en verleng hem met de lengte gegeven in de Extender
Note: Rotator / Draait de lijn 270 graden
Rotator
    ANGLE = 270
    XORIG = @Value(x)
    YORIG = @Value(y)
    ROTATED -> Counter
Note: Counter / Geeft de Dwarsprofiellijnen het ID mee: 'DwarsProfNr'
Counter
    CNT_ATTR = DwarsProfNr
    DOMAIN = counter
    SCOPE = Global
    START = 0
    -> Extender
    -> AttributeManager_4
Note: Extender / Verlengt de lijn tot een gespecificeerde lengte / Nu gekozen voor 25 meter
Extender
    LEN = 25
    BEGINNING -> AttributeManager_3
    END -> AttributeManager_5
    STRETCHED -> Bufferer_2
    STRETCHED -> AttributeManager_2
    <REJECTED> -> Extender__Rejected_
Extender__Rejected_: Inspector [off]

Bookmark: Bepaal of Punten Links, Midden of Rechts van een HydroObject liggen
  Ten behoeve van Sortering punten van links naar rechts ten opzichte van de stroomrichting van het HydroObject
Note: AttributeManager_4 / Verwijdert alle attributen behalve / DwarsprofielNr en voegt 'HydroObjectZijde' met de waarde 'Midden' toe
AttributeManager_4
    ATTR_TABLE:
      REMOVE Code
      REMOVE HyOb_Code
      REMOVE HyOb_Naam
      REMOVE OBJECTID
      REMOVE x
      REMOVE y
      REMOVE _z
      REMOVE OBJECTID_1
      REMOVE Naam
      REMOVE InModel
      REMOVE _clipped
      SET_TO HydroObjectZijde = Midden
    -> PointOnLineOverlayer [LINE]
Note: AttributeManager_3 / Verwijdert alle attributen behalve / DwarsprofielNr en voegt 'HydroObjectZijde' met de waarde 'Links' toe
AttributeManager_3
    ATTR_TABLE:
      REMOVE Code
      REMOVE HyOb_Code
      REMOVE HyOb_Naam
      REMOVE OBJECTID
      REMOVE x
      REMOVE y
      REMOVE _z
      REMOVE OBJECTID_1
      REMOVE Naam
      REMOVE InModel
      REMOVE _clipped
      SET_TO HydroObjectZijde = Links
    -> PointOnLineOverlayer [LINE]
Note: AttributeManager_5 / Verwijdert alle attributen behalve / DwarsprofielNr en voegt 'HydroObjectZijde' met de waarde 'Rechts' toe
AttributeManager_5
    ATTR_TABLE:
      REMOVE Code
      REMOVE HyOb_Code
      REMOVE HyOb_Naam
      REMOVE OBJECTID
      REMOVE x
      REMOVE y
      REMOVE _z
      REMOVE OBJECTID_1
      REMOVE Naam
      REMOVE InModel
      REMOVE _clipped
      SET_TO HydroObjectZijde = Rechts
    -> PointOnLineOverlayer [LINE]
Note: PointOnLineOverlayer / Legt de gecreeerde punten over de lijnen om / zo het attribuutLinkerpunten, Rechterpunten of / Middenpunten te kunnen vullen
PointOnLineOverlayer
    ATTR_ACCUM_MODE = Merge Incoming
    ATTR_CONFLICT_RES = Use Original
    OV_ATTR = _overlaps
    TOLERANCE = 0.01
    POINT -> TestFilter
    <REJECTED> -> PointOnLineOverlayer__Rejected_
PointOnLineOverlayer__Rejected_: Inspector [off]

Bookmark: Combineer Lijnen
Note: Bufferer_2 / Zet een buffer van 0.01 m rondom de / dwarsprofiellijn, zodat er geen onnnodige / overlaps worden meegenomen
Bufferer_2
    CAP_STYLE = Round
    INTERP_SEGMENTS = 8
    OFFSET = 0.01
    BUFFERED -> Clipper_2 [CLIPPER]
Note: AttributeManager / Verwijdert onnodige attributen / en geeft blijvende attributen de / voorloper _Dwars (voor dwarsprofiel)
AttributeManager_2
    ATTR_TABLE:
      RENAME_SET_VALUE Code > Dwars_Code
      RENAME_SET_VALUE HyOb_Code > Dwars_HyOb_Code
      RENAME_SET_VALUE HyOb_Naam > Dwars_HyOb_Naam
      REMOVE OBJECTID
      REMOVE x
      REMOVE y
      REMOVE _z
      REMOVE OBJECTID_1
      RENAME_SET_VALUE Naam > Dwars_Naam
      REMOVE InModel
      REMOVE _clipped
    -> LineOnLineOverlayer_2 [LINE]
Note: Input Lengteprofiel
Note: Counter_2 / Geeft de lengteprofielen het ID mee: / 'LengteProf_Counter'
Counter_2
    CNT_ATTR = LengteProf_Nr
    DOMAIN = counter
    SCOPE = Global
    START = 0
    -> Clipper_2 [CLIPPEE]
Note: Clipper_2 / Clipt het lengteprofiel dat binnen de buffer valt / en dus direct bij een dwarsprofiellijn ligt
Clipper_2
    ATTR_ACCUM_MODE = Merge Clipper
    ATTR_CONFLICT_RES = Use Clippee
    BOUNDARY_CASES = Treat as Inside
    CLIPPED_ATTR = _clipped
    CLIP_TYPE = Multiple Clippers
    CONNECT_Z_MODE = First Wins
    CREATE_AGGREGATES = Yes
    LINES_AS_SEGMENTS = No
    PRESERVE_CLIPPEE_EXTENTS = No
    INSIDE -> AttributeManager
Note: AttributeManager / Verwijdert onnodige attributen / en geeft blijvende attributen de / voorloper _PRof (voor lengteprofiel)
AttributeManager
    ATTR_TABLE:
      RENAME_SET_VALUE OBJECTID > Prof_OBJECTID
      RENAME_SET_VALUE WS_CODE > Prof_WS_CODE
      REMOVE WS_VERVALDATUM
      RENAME_SET_VALUE WS_SOORTLANDMEETLIJN > Prof_SoortLandmeetLijn
      REMOVE WS_BRON
      REMOVE WS_OPMERKING
      REMOVE WS_INWINNINGSDATUM
      REMOVE CODEHISTORIE
      REMOVE CREATED_USER
      REMOVE CREATED_DATE
      REMOVE LAST_EDITED_USER
      REMOVE LAST_EDITED_DATE
      RENAME_SET_VALUE _clipped > Prof_clipped
    -> LineOnLineOverlayer_2 [LINE]
Note: LineOnLineOverlayer_2 / Legt de geclipte lengteprofielen en de / dwarsprofielen over elkaar heen, en creëert / punten op de kruispunten
LineOnLineOverlayer_2
    ATTRS_ACCUM_MODE = Merge Attributes
    DEAGGREGATE_INPUT = Yes
    GENERATE_LIST_DROP = NO
    INCOMING_PREFIX = LOL_
    LOG_LEVEL = Full
    OV_ATTR = _overlaps
    SEPARATE_COLLINEAR_SEGMENTS = No
    POINT -> Tester
Note: Tester / Test of de overlap juist is door te testen / of de ID's Lengteprof / en DwarsProfNR een waarde hebben
Tester
    BOOL_OP = AND
    TEST_CLAUSE:
      TEST @Value(LengteProf_Nr) ATTRIBUTE_HAS_VALUE ""
      TEST @Value(DwarsProfNr) ATTRIBUTE_HAS_VALUE ""
    PASSED -> PointOnLineOverlayer [POINT]

Bookmark: Test GW PRO data
Note: Tester_7 / Test of het om een Dwarsprofiel / of een Lengteprofiel gaat
Tester_7
    BOOL_OP = OR
    TEST_CLAUSE = TEST @Value(PROIDENT) BEGINS_WITH DP
    FAILED -> Tester_5

Bookmark: Test Jaartal '
Tester_5
    BOOL_OP = OR
    TEST_CLAUSE = TEST @Value(OPRDATOP) > 20000608000000
    PASSED -> Counter_2

Bookmark: Meet afstand van het punt tot de MeetLocatie
  Ten behoeve van Sortering punten van links naar rechts ten opzichte van de stroomrichting van het HydroObject
Note: TestFilter
TestFilter
    DEFAULT_VALUE = <UNFILTERED>
    TEST_LIST = BOOL_OP,OR,COMPOSITE_TEST,<Unused>,TEST_CLAUSE,"TEST @Value(HydroObjectZijde) = Links",LinkerPunten,BOOL_OP,OR,COMPOSITE_TEST,<Unused>,TEST_CLAUSE,"TEST @Value(HydroObjectZijde) = Midden",MiddenPunten,BOOL_OP,OR,COMPOSITE_TEST,<Unused>,TEST_CLAUSE,"TEST @Value(HydroObjectZijde) = Rechts",RechterPunten
    LinkerPunten -> NeighborFinder [BASE]
    MiddenPunten -> NeighborFinder [BASE]
    RechterPunten -> NeighborFinder [BASE]
Note: NeighborFinder / Meet de afstand van de punten ten opzichte van de DwarsprofielLocaties
NeighborFinder
    ATTR_ACCUM_MODE = Merge Candidate
    ATTR_CONFLICT_RES = Use Base
    CANDIDATES_FIRST = No
    INSERT_VERTEX = No
    K = 1
    MODE = Bases and Candidates
    TREAT_POLYGON_AS = Lines
    MATCHED -> AttributeCreator

Bookmark: Sorteer punten
Note: AttributeCreator / Maakt twee nieuwe waardes aan: / 'AfstandLinks' en 'AfstandRechts' en / vult hier een conditionele waarde in: / De afstand tot van het punt tot de / HydroObjec-lijn, afhankelijk van of het punt / links of rechts van de lijn ligt.
AttributeCreator
    ATTR_TABLE:
      SET_TO AfstandLinks = FME_CONDITIONAL:DEFAULT_VALUE'_FME_NO_OP_'BOOL_OP;OR;COMPOSITE_TEST;<Unused>;TEST @Value(HydroObjectZijde) = Links'@Value(_distance)'FME_NUM_CONDITIONS2___
      SET_TO AfstandRechts = FME_CONDITIONAL:DEFAULT_VALUE'_FME_NO_OP_'BOOL_OP;OR;COMPOSITE_TEST;<Unused>;TEST @Value(HydroObjectZijde) = Rechts'@Value(_distance)'FME_NUM_CONDITIONS2___
    -> Sorter
Note: Sorter / Sorteerd de DwarsprofielPunten / van links naar rechts op basis van de volgende / attributen: / 1. Dwarsprofielnummer / 2. AfstandLinks -> Aflopend / 3. AfstandRechts -> Oplopend
Sorter
    SORT_PARM = DwarsProfNr NUMERIC ASCENDING HydroObjectZijde ALPHA ASCENDING AfstandLinks NUMERIC DESCENDING AfstandRechts NUMERIC ASCENDING
    SORTED -> AttributeCreator_2

Bookmark: Geef punten een opeenvolgend nummer per dwarsprofiel
Note: AttributeManager_6 / Verwijdert onnodige attributen
AttributeManager_6
    ATTR_TABLE:
      REMOVE Code
      REMOVE _angle
      REMOVE _candidate_angle
      REMOVE _candidate_label_angle
      REMOVE _closest_candidate_x
      REMOVE _closest_candidate_y
      REMOVE _closest_base_x
      REMOVE _closest_base_y
    -> Counter_3
Note: Counter_3 / Telt de punten per Dwarsprofielnummer / op volgorde van de sortering
Counter_3
    CNT_ATTR = DwarsprofielPunt_count
    DOMAIN = @Value(DwarsProfNr)counter
    SCOPE = Global
    START = 0
    -> AttributeManager_7

Bookmark: Opschonen attributen en toevogen X, Y, Z
Note: AttributeManager_7 / Hernoemt attributen en / verwijdert onnodige attributen
AttributeManager_7
    ATTR_TABLE:
      SET_TO Code = @Value(DwarsProfNr)_@Value(DwarsprofielPunt_count)
      RENAME_SET_VALUE DwarsprofielPunt_count > VolgNummer
      SET_TO DwarsProfNr > ProfielCode = PM_@Value(DwarsProfNr)
      SET_TO TypeProfiel = dwarsprofiel
      SET_TO HerkomstProfiel = interpolatie
      RENAME_SET_VALUE HyOb_Code > HydroObject_Code
      REMOVE AfstandLinks
      REMOVE AfstandRechts
      RENAME_SET_VALUE Prof_SoortLandmeetLijn > SoortLandmeetLijn
      REMOVE Prof_OBJECTID
      REMOVE Prof_WS_CODE
      REMOVE Prof_clipped
      REMOVE LengteProf_Nr
      REMOVE Dwars_Code
      REMOVE Dwars_HyOb_Code
      REMOVE Dwars_HyOb_Naam
      REMOVE Dwars_Naam
      REMOVE _overlaps
      REMOVE HydroObjectZijde
      REMOVE HyOb_Naam
      REMOVE _distance
      RENAME_SET_VALUE Administatiefgebiedid > administratiefgebied = limburg
    -> CoordinateExtractor_2
Note: CoordinateExtractor_2 / Voegt de x, y en z coordinaat toe / als attribuut
CoordinateExtractor_2
    IND = 0
    MODE = Specify Coordinate
    X_ATTR = xCoord
    Y_ATTR = yCoord
    Z_ATTR = zCoord
    -> FeatureMerger [REQUESTOR]
    -> ListBuilder

Bookmark: Test hoeveel lengteprofielen er gekruist worden (minder dan 4 wordt niet meegenomen)
Note: ListBuilder / Groepeert de Dwarsprofielpunten / op basis van het 'DwarsProfNr'
ListBuilder
    GRP_BY = DwarsProfNr
    LIST_NAME = _list
    -> ListElementCounter
Note: ListElementCounter / bepaalt hoeveel punten er in / één dwarsprofiel zitten door aantal / punten in de list te tellen
ListElementCounter
    CNT_ATTR = _element_count
    LIST_NAME = _list{}
    -> Tester_4
Note: Tester_4 / Test of het aantal dwarsprofiel- / punten 3 of meer is, alleen bij meer / dan drie worden ze weggeschreven / (Passed)
Tester_4
    BOOL_OP = OR
    TEST_CLAUSE = TEST @Value(_element_count) > 3
    PASSED -> ListExploder_2
Note: ListExploder_2 / Splitst de gegroepeerde / punten weer
ListExploder_2
    ATTR_ACCUM_MODE = Merge Incoming List
    ATTR_CONFLICT_RES = Use Incoming List
    INDEX_ATTR = _element_index
    LIST_ATTR = _list{}
    ELEMENTS -> AttributeManager_8
Note: AttributeManager_8 / Verwijdert onnodige attributen
AttributeManager_8
    ATTR_TABLE:
      REMOVE DwarsProfNr
      REMOVE VolgNummer
      REMOVE ProfielCode
      REMOVE TypeProfiel
      REMOVE HerkomstProfiel
      REMOVE HydroObject_Code
      REMOVE xCoord
      REMOVE yCoord
      REMOVE zCoord
      REMOVE _element_count
      REMOVE _element_index
      SET_TO administratiefgebied = limburg
    -> FeatureMerger [SUPPLIER]
Note: FeatureMerger / Voegt de punten samen met de punten / die aan de voorwaarde voldoen (minimaal 3 / punten per dwarsprofiel)
FeatureMerger
    ATTR_ACCUM_MODE = Merge Supplier
    ATTR_CONFLICT_RES = Use Requestor
    IGNORE_NULLS = No
    JOIN_KEYS = @Value(Code) @Value(Code) AUTO
    MERGE_TYPE = Attributes Only
    PROCESS_DUPS = No
    REJECT_NULL_MISSING_KEYS = No
    SUPPLIERS_FIRST = No
    MERGED -> AttributeManager_9
Note: Statusobject omzetting naar text
AttributeManager_9
    ATTR_TABLE:
      RENAME_SET_VALUE VolgNummer > codevolgnummer
      SET_TO Ruwheidstypecode = @LowerCase(@Value(Ruwheidstypecode))
      SET_TO StatusObjectCode > statusobjectcode = FME_CONDITIONAL:DEFAULT_VALUE'onbekend'BOOL_OP;OR;COMPOSITE_TEST;<Unused>;TEST @Value(StatusObjectCode) = 1'planvorming'BOOL_OP;OR;COMPOSITE_TEST;<Unused>;TEST @Value(StatusObjectCode) = 3'gerealiseerd'BOOL_OP;OR;COMPOSITE_TEST;<Unused>;TEST @Value(StatusObjectCode) = 4'buiten bedrijf'BOOL_OP;OR;COMPOSITE_TEST;<Unused>;TEST @Value(StatusObjectCode) = 5'niet meer aanwezig'BOOL_OP;OR;COMPOSITE_TEST;<Unused>;TEST @Value(StatusObjectCode) = 7'te verwijderen'FME_NUM_CONDITIONS6___
      SET_TO typeprofielcode = waterloop
    -> dwarsprofielpunten_interpolatie (writer FILEGDB_3)
