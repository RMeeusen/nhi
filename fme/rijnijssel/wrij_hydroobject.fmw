FME workspace wrij_hydroobject.fmw

Parameters:
- SourceDataset_ARCGIS_LAYER = Database Connections\Connection to blaeu-prod-db.sde\BLAEU.GW_OVK   # Source Esri ArcGIS Layer
- SourceDataset_ARCGIS_LAYER_5 = Database Connections\Connection to blaeu-prod-db.sde\BLAEU.GW_OWA   # Source Esri ArcGIS Layer
- DestDataset_ESRISHAPE = $(FME_MF_DIR)checks   # Destination Esri Shapefile Folder
- SourceDataset_ARCGIS_LAYER_7 = X:\ArcGIS\Layer\Watersystemen\Beheerregister\Leidingvak (beheerregister watersysteem).lyr   # Source Esri ArcGIS Layer
- SourceDataset_ARCGIS_LAYER_6 = X:\ArcGIS\Layer\Watersystemen\Beheerregister\Watergang (beheerregister watersysteem).lyr   # Source Esri ArcGIS Layer
- DestDataset_GML2 = G:\GIS WATERSYSTEEM\HyDAMO\FME\gml\wrij_hydroobject.gml   # Destination Geography Markup Language (GML) v2.1.2 File
- DestDataset_GML2_3 = G:\GIS WATERSYSTEEM\HyDAMO\FME\gml\wrij_hydroobject.gml   # Destination Geography Markup Language (GML) v2.1.2 File

Readers:
- ARCGIS_LAYER_1: ARCGIS_LAYER from $(SourceDataset_ARCGIS_LAYER) in "ESRIWKT|RD_New|PROJCS["RD_New",GEOGCS["GCS_Amersfoort",DATUM["D_Amersfoort",SPHEROID["Bessel_1841",6377397.155,299.1528128]],PRIMEM["Greenwich",0.0],UNIT["Degree",0.0174532925199433]],PROJECTION["Double_Stereographic"],PARAMETER["False_Easting",155000.0],PARAMETER["False_Northing",463000.0],PARAMETER["Central_Meridian",5.38763888888889],PARAMETER["Scale_Factor",0.9999079],PARAMETER["Latitude_Of_Origin",52.15616055555555],UNIT["Meter",1.0]]"
- ARCGIS_LAYER_2: ARCGIS_LAYER from $(SourceDataset_ARCGIS_LAYER_5)
- ARCGIS_LAYER_3: ARCGIS_LAYER from $(SourceDataset_ARCGIS_LAYER_7)
- ARCGIS_LAYER_4: ARCGIS_LAYER from $(SourceDataset_ARCGIS_LAYER_6)

Writers:
- ESRISHAPE_1: ESRISHAPE to $(DestDataset_ESRISHAPE) in EPSG:28992
- GML2_1: GML2 to $(DestDataset_GML2) in EPSG:28992
- GML2_2: GML2 to $(DestDataset_GML2_3) in EPSG:28992

Note: Lijsten / KSTSOORT (Soort stuw: BLS_STUW_SOORTEN) / 1 = schotbalkstuw / 2 = stuw met schuif / 3 = stuw met klep / 4 = segmentstuw / 5 = cascadestuw / 6 = hevelstuw / 7 = meetstuw / 8 = meetschot / 9 = stuw met contra-gewicht / 10 = inlaat- en/of aflaatstuw / 11 = overlaat / 12 = drijverstuw / 15 = kantelstuw / 70 = knijpstuw / 71 = samengestelde stuw / 98 = overig / 99 = onbekend / KSTREGEL (regelbaarheid: BLS_REGELBAARHEID_SOORTEN_VOO) / 1 = vaste stuw / 2 = regelbaar stuw, niet automatisch / 3 = regelbaar stuw, automatisch / 4 = handmatig / 99 = overig / IWS_LEGGERSTATUS (Leggerstatus: BLS_LEGGERSTATUS) / 1 = vastgesteld / 2 = gewijzigd / 3 = verwijderd / 4 = niet van toepassing / KWKSTATU (Ind. status kunstwerk: BLS_PLANSTATUS_INCL_ONBEKEND_) / 100 = planvorming / 201 = realisatie plan (lange termijn) / 202 = realisatie plan (middellange termijn) / 203 = realisatie plan (korte termijn) / 204 = realisatie plan (in uitvoering) / 300 = gerealiseerd/in bedrijf/in gebruik/operationeel / 400 = buiten bedrijf/gesloten / 500 = niet meer aanwezig / 9800 = onbekend / 9900 = overig / KDUVORM (duikervorm: BLS_VORMEN) / 1 = rond / 2 = rechthoekig / 3 = eivormig / 4 = muil / 5 = ellips / 6 = heul / 7 = pyramide / 98 = Overig / 99 = onbekend / KSTKRVRM (Kruinvorm: BLS_KRUINVORMEN) / 1 = rechthoek / 2 = driehoek / 3 = trapezium / 4 = parabool / 5 = cirkel / 6 = kruin met speciale vorm / 10 = rechthoek verdiept / 11 = trapezium verdiept / 99 = onbekend / KDUAFSLx (Afsluitwijze: BLS_AFSLUITWIJZEN) / 1 = deur / 2 = schotbalk / 3 = zandzakken / 4 = verticale schuif / 5 = terugslagklep / 6 = tolklep / 7 = spindel / 50 = niet afsluitbaar / 99 = overig / KDUAFSBE (Afsluiting benedenstrooms: BLS_AFSLUITING_DUIKERS) / 1 = schotbalksponning / 2 = schuif / 3 = afsluiter / 4 = terugslagklep / 98 = overig / 99 = onbekend

Bookmark: Stap 1: inlezen GeoNIS
  Inlezen rechtstreeks uit OracleDatabase en ophalen Attributes die gebruikt worden, de rest niet.
  BLAEU.GW_OVK
  Dit zijn de Leidingvakken en vormt de basis voor hydroobject
  BLAEU.GW_OWA
  Dit zijn de Waterlopen en wordt alleen gebruikt om op basis van een Spatial Join de naam van de waterloop over te halen naar hydroobject.
BLAEU.GW_OVK (reader ARCGIS_LAYER_1) [off]
    attributes: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
Leidingvak (beheerregister watersysteem) (reader ARCGIS_LAYER_3)
    attributes: AARD char(3), ADMINNAUWKEURIGHEID integer, AVVBERMT integer, AVVBODDR float, AVVBODH float, AVVDIEPT float, AVVDROOB integer, AVVDROOE integer, AVVGEMBH float, AVVHOBES float, AVVHOBOS float, AVVHYDST float, AVVKNKL_L float, AVVKNKL2_L float, AVVKNKR_L float, AVVKNKR2_L float, AVVNATOM float, AVVNATOP float, AVVSNELH float, AVVTALL2_L float, AVVTALR2_L float, AVVTALUL float, AVVTALUR float, AVVVERHG float, AVVWNTPL float, AVVWRHFC float, AVVZMRPL float, BAGCYCL integer, BAGGERTRANSPORT integer, BETROUWBAARHEID integer,
      BOH_MUT_JAAR integer, BOHINR_BIJZ_LNG double, BOHINR_BIJZ_TXT char(50), BOHINR_JJEVEN integer, BOHINR_JJONEVEN integer, BOHINR_STATUS integer, BOHINR_TYPE integer, BRON char(255), COMBITYPE_KRW_VISMIG_NTW integer, CREATED_DATE date, CREATED_USER char(50), GEB_FUNCTIE char(2), GEONAUWKEURIGHEID integer, GEONAUWKEURIGHEID_Z integer, GLOBALID char(38), IDEALISATIE integer, INWINNINGSDATUM date, INWINNINGSWIJZE integer, IWS_AVVHOBES_L float, IWS_AVVHOBOS_L float, IWS_BEGIN_AFSTAND integer, IWS_BESCHZONEBI float, IWS_BESCHZONEBU float, IWS_BOV_BR integer, IWS_BOVENBREEDTE_KANT_INSTEEK float, IWS_BREEDTE float, IWS_CATEGORIEEN integer, IWS_CLASSIFICATIE_WATERVOERING integer, IWS_EIGENAAR char(255), IWS_EIND_AFSTAND integer,
      IWS_GEOGRAFLIGGING integer, IWS_KWLTGEO integer, IWS_LEGGERSTATUS integer, IWS_LENGTE double, IWS_MAAIVELD_BENEDENSTROOMS float, IWS_MAAIVELD_BOVENSTROOMS float, IWS_MEMO char(2000), IWS_OWASRTKN integer, IWS_STATUSTEKST char(2000), IWS_TOEGANKELIJK integer, IWS_VAKTYPE integer, IWS_W_BRPLASBL float, IWS_W_BRPLASBR float, IWS_W_INSTHGTEL float, IWS_W_INSTHGTER float, IWS_W_PLASBH_DL float, IWS_W_PLASBH_DR float, IWS_W_PLASBTALL float, IWS_W_PLASBTALR float, IWS_W_REFPEIL integer, IWS_W_WATBRREFP float, IWS_W_WATPEIL float, IWS_ZSTRAF integer, IWS_ZSTRAN integer, KWKSTATU integer, LAST_EDITED_DATE date, LAST_EDITED_USER char(50), LEG_GEREED_VOOR_CL integer, LEG_ZIENSWIJZE integer, MIGRTYPE_KRW_VISMIG_NTW integer,
      MOH_MUT_JAAR integer, MOHINR_BIJZ_LNG double, MOHINR_BIJZ_TXT char(50), MOHINR_JJEVEN integer, MOHINR_JJONEVEN integer, MOHINR_STATUS integer, NETWERK_ECOLOGIE integer, NETWERK_KRW_VISMIGRATIE integer, OBJECTID integer, OH_BAGGERPL char(50), OH_PAKKET char(6), OH_PAKKET_BASIS char(6), OHBLD_P1 integer, OHBLD_P2 integer, OHBLD_P3 integer, OHBLD_P4 integer, OHINR_TYPE integer, OPMERKINGEN char(255), OSMOMSCH char(60), OVK_TYPE char(10), OVKIDENT char(24), OVKLENGT integer, OVKSOORT integer, OWA_OWA_ID guid, OWM_OWM_ID guid, QSCAN_BLD_DATE char(10), QSCAN_BLD_TOETS integer, RICHTING float, SHAPE.LEN double, STEDELIJK_WATER_OVK integer,
      STR_BLD_CODE integer, STR_BLD_DATE char(10), STR_BLD_OPMERK char(50)
    -> AttributeFilter_OVK
BLAEU.GW_OWA (reader ARCGIS_LAYER_2) [off]
    attributes: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
Watergang (beheerregister watersysteem) (reader ARCGIS_LAYER_4)
    attributes: ADMINNAUWKEURIGHEID integer, BETROUWBAARHEID integer, BRON char(255), CREATED_DATE date, CREATED_USER char(50), GEONAUWKEURIGHEID integer, GEONAUWKEURIGHEID_Z integer, GLOBALID char(38), IDEALISATIE integer, INWINNINGSDATUM date, INWINNINGSWIJZE integer, IOTW_CODE char(24), IWS_BOUWJAAR integer, IWS_DIEPSTE_PUNT char(10), IWS_EIGENAAR char(255), IWS_GEM_BODHO_VLAKTE float, IWS_KWLTGEO integer, IWS_LEGGERSTATUS integer, IWS_MEMO char(2000), IWS_STATUS integer, IWS_STATUSTEKST char(2000), LAST_EDITED_DATE date, LAST_EDITED_USER char(50), LBISTATG integer, OBJECTID integer, OPMERKINGEN char(255), OWA_TYPE char(10), OWAAFLAA float, OWABERGW double, OWABERGZ double,
      OWACATEG integer, OWADATVL date, OWAFUNC1 integer, OWAFUNC2 integer, OWAFUNC3 integer, OWAFUNCT char(6), OWAIDENT char(24), OWAINLAA float, OWAINOOR integer, OWAJAAR integer, OWALENGT integer, OWANAAM char(50), OWANIVO char(10), OWAOPME char(50), OWAOPPVL integer, OWARIJK integer, OWASGCAT integer, OWASRTKL integer, OWASRTKN integer, OWASRTVO integer, OWASTRAF integer, OWASTRAN integer, OWAVOLUM double, OWAWATST float, OWLBODHO float, OWM_OWM_ID guid, RICHTING float, SHAPE.LEN double, STEDELIJK_WATER_OWA integer, WBHCODE integer,
      WGBIDENT char(24)
    -> AttributeFilter_OWA

Bookmark: Stap2: filteren Attributen
  De actuele Objecten worden eruit gefilterd en verder verwerkt.
  De historische Objecten worden eventueel later toegevoegd om geschiedenis mee te nemen in database.
Note: Filter KWKSTATU / 100 = planvorming / 201 = realisatie plan (lange termijn) / 202 = rp (middellange termijn) / 203 = rp (korte termijn) / 204 = rp (in uitvoering) / 300 = gerealiseerd / 400 = buiten bedrijf / gesloten / 500 = niet meer aanwezig / 9800 = onbekend / 9900 = overig
AttributeFilter_OVK
    ATTR_VALUES = <EMPTY>,<MISSING>,<UNFILTERED>,400,500,100,201,202,203,204,300,9800,9900,<NULL>
    ATTR_NAME = KWKSTATU
    <EMPTY> -> AttributeFilter_OVK__EMPTY__-__Trash_OVK
    <MISSING> -> AttributeFilter_OVK__EMPTY__-__Trash_OVK
    <UNFILTERED> -> AttributeFilter_OVK__EMPTY__-__Trash_OVK
    400 -> AttributeFilter_OVK__EMPTY__-__Trash_OVK
    500 -> AttributeFilter_OVK__EMPTY__-__Trash_OVK
    100 -> AttributeFilter_OVK__EMPTY__-__Trash_OVK
    201 -> AttributeCreator_Use_OVK
    202 -> AttributeCreator_Use_OVK
    203 -> AttributeCreator_Use_OVK
    204 -> AttributeCreator_Use_OVK
    300 -> AttributeCreator_Use_OVK
    9800 -> AttributeCreator_Use_OVK
    9900 -> AttributeCreator_Use_OVK
    <NULL> -> AttributeCreator_Use_OVK
AttributeFilter_OVK__EMPTY__-__Trash_OVK: Junction
    -> Trash_OVK
Trash_OVK: Inspector [off]
AttributeCreator_Use_OVK
    -> AttributeValidator_OVK
Note: Filter IWS_LEGGERSTATUS / 1 = Vastgesteld / 2 = Gewijzigd / 3 = Verwijderd / ? = Niet in de Legger (buiten beheergebied)
AttributeFilter_OWA
    ATTR_VALUES = 1,2,<NULL>,<EMPTY>,<MISSING>,<UNFILTERED>,3,71
    ATTR_NAME = IWS_LEGGERSTATUS
    1 -> Tester_NotIJssel
    2 -> Tester_NotIJssel
    <NULL> -> Tester_NotIJssel
    <EMPTY> -> AttributeFilter_OWA__EMPTY_
    <MISSING> -> AttributeFilter_OWA__EMPTY_
    <UNFILTERED> -> AttributeFilter_OWA__EMPTY_
    3 -> AttributeFilter_OWA__EMPTY_
    71 -> AttributeFilter_OWA__EMPTY_
Note: IJSSEL wordt niet meegenomen omdat deze geen geografische data bevat.
Tester_NotIJssel
    TEST_MODE = Automatic
    BOOL_OP = OR
    TEST_DESCRIPTION = ""
    TEST_CLAUSE = TEST @Value(OWANAAM) != IJSSEL
    PASSED -> AttributeCreator_Use_OWA
AttributeCreator_Use_OWA
    -> AttributeValidator_OWA
AttributeFilter_OWA__EMPTY_: Junction
    -> Trash_OWA
Trash_OWA: Inspector

Bookmark: Stap 3: Check Compleetheid
  Check of de gebruikte Attributes compleet gevuld zijn met data.
AttributeValidator_OVK
    TABLE = LAST_EDITED_DATE,KWKSTATU,CREATED_DATE,OVKIDENT;ATTRIBUTE_NOT_NULL;<Unused>
    PASSED -> AttributeValidator_OVK_PASSED
    FAILED -> AttributeValidator_OVK_PASSED
    FAILED -> GW_OVK_Nulls (writer ESRISHAPE_1)
GW_OVK_Nulls (writer ESRISHAPE_1) [off]
    attributes: OVKIDENT char(24), KWKSTATU long, CREATED_DA date, LAST_EDITE date
AttributeValidator_OVK_PASSED: Junction
    -> AttributeCreator_OVK
AttributeValidator_OWA
    TABLE = OWAIDENT,IWS_LEGGERSTATUS,OWANAAM;ATTRIBUTE_NOT_NULL;<Unused>
    PASSED -> Junction
    FAILED -> Junction
    FAILED -> GW_OWA_Nulls (writer ESRISHAPE_1)
Junction
    -> AttributeCreator_OWA
GW_OWA_Nulls (writer ESRISHAPE_1) [off]
    attributes: OWAIDENT char(24), OWANAAM char(50), IWS_LEGGER long

Bookmark: Stap 4: Null-velden vullen
  Velden zonder waarde (Null) worden met Dummy waarden gevuld of met waarden van een ander Attribuut.
AttributeCreator_OVK
    ATTR_TABLE:
      SET_TO OVKIDENT = @Value(OVKIDENT)
      SET_TO KWKSTATU = FME_CONDITIONAL:DEFAULT_VALUE'_FME_NO_OP_'BOOL_OP;OR;COMPOSITE_TEST;<Unused>;TEST KWKSTATU ATTRIBUTE_VALUE_NULL _FME_BLANK_STRING_'300'FME_NUM_CONDITIONS2___
      SET_TO CREATED_DATE = FME_CONDITIONAL:DEFAULT_VALUE'_FME_NO_OP_'BOOL_OP;OR;COMPOSITE_TEST;<Unused>;TEST CREATED_DATE ATTRIBUTE_VALUE_NULL _FME_BLANK_STRING_'19000101000000'FME_NUM_CONDITIONS2___
      SET_TO LAST_EDITED_DATE = FME_CONDITIONAL:DEFAULT_VALUE'_FME_NO_OP_'BOOL_OP;OR;COMPOSITE_TEST;<Unused>;TEST LAST_EDITED_DATE ATTRIBUTE_VALUE_NULL _FME_BLANK_STRING_'@Value(CREATED_DATE)'FME_NUM_CONDITIONS2___
    -> Tester_DatumCheck
    -> AttributeCreator_OVK_Output
AttributeCreator_OVK_Output: Inspector
AttributeCreator_OWA
    ATTR_TABLE = SET_TO OWANAAM = FME_CONDITIONAL:DEFAULT_VALUE'_FME_NO_OP_'BOOL_OP;OR;COMPOSITE_TEST;<Unused>;TEST OWANAAM ATTRIBUTE_VALUE_NULL _FME_BLANK_STRING_'NoName'FME_NUM_CONDITIONS2___
    -> Bufferer_2m
    -> AttributeCreator_OWA_Output
AttributeCreator_OWA_Output: Inspector [off]

Bookmark: Stap 5: Check plausibiliteit
  Diverse plausibiliteitschecks kunnen hier gedefinieerd worden.
Tester_DatumCheck
    TEST_MODE = Automatic
    BOOL_OP = OR
    TEST_DESCRIPTION = ""
    TEST_CLAUSE = TEST @Value(CREATED_DATE) <= @Value(LAST_EDITED_DATE)
    PASSED -> Tester_DatumCheck_PASSED
    FAILED -> AttributeCreator_DatumCorrectie

Bookmark: Stap 6: Correctie niet-plausibele waarden
  Falen van plausibiliteitschecks worden in deze stap al dan niet automatisch gecorrigeerd.
AttributeCreator_DatumCorrectie
    ATTR_TABLE = SET_TO CREATED_DATE = @Value(LAST_EDITED_DATE)
    -> Tester_DatumCheck_PASSED
Tester_DatumCheck_PASSED: Junction
    -> Tester_DatumCheck_PASSED_Output

Bookmark: Stap 7: Transformaties naar HyDAMO
  Alle benodigde HyDAMO Attributen worden via Transformaties aangemaakt.
Tester_DatumCheck_PASSED_Output: Junction
    -> SpatialFilter [Candidate]
Note: Buffer aanmaken om SpatialFiltering te verbeteren
Bufferer_2m
    OFFSET = 2
    INTERP_SEGMENTS = 8
    CAP_STYLE = Round
    BUFFERED -> Bufferer_2m_2
Bufferer_2m_2: Junction
    -> SpatialFilter [Filter]
    -> Bufferer_2m_Output
Note: OVK = Candidate / OWA_Buff = Filter
SpatialFilter
    PREDICATE_VALUE = Contains
    USE_BOUNDING_BOX = No
    BASE_TYPE = Multiple Filters
    CURVE_BOUNDARY_RULE_PARAM = Default Rule
    PASS_CRITERIA = Pass Against One Filter
    PREDATTR = _predicate
    MERGE_ATTRS = Yes
    PASSED -> AttributeCreator_Transformaties_HyDAMO
    FAILED -> SpatialFilter_Failed
    FAILED -> SpatialFilter_Failed (writer ESRISHAPE_1)
Note: Filter KWKSTATU / 100-203 = 1-planvorming / 204, 300, 9800, 9900 = 3-gerealiseerd / 4-buiten bedrijf, 5-niet meer aanwezig, 7-te verwijderen en 98-onbekend worden voorlopig niet gebruikt.
AttributeCreator_Transformaties_HyDAMO
    ATTR_TABLE:
      SET_TO code = @Value(OVKIDENT)
      SET_TO naam = @Value(OWANAAM)
      SET_TO statusobjectcode = FME_CONDITIONAL:DEFAULT_VALUE'FME_NULL_VALUE'BOOL_OP;OR;COMPOSITE_TEST;<Unused>;TEST @Value(KWKSTATU) RANGE [100,203]'planvorming'BOOL_OP;OR;COMPOSITE_TEST;<Unused>;TEST @Value(KWKSTATU) > 203'gerealiseerd'FME_NUM_CONDITIONS3___
      SET_TO objectbegintijd = @Value(CREATED_DATE)
      SET_TO objecteindtijd = @Value(LAST_EDITED_DATE)
      SET_TO hyperlink = dummy
      SET_TO administratiefgebied = rijn en ijssel
      SET_TO ruwheidstypecode = stricklerks
      SET_TO ruwheidswaardelaag = 25
      SET_TO ruwheidswaardehoog = 15
    -> hydroobject
    -> hydroobject (writer GML2_2)
SpatialFilter_Failed: Inspector [off]
SpatialFilter_Failed (writer ESRISHAPE_1) [off]
    attributes: OVKIDENT char(24), KWKSTATU long
Bufferer_2m_Output: Inspector [off]

Bookmark: Stap 8: Write GML
  Op basis van GML Writer wordt in deze stap de GML aangemaakt.
hydroobject: Inspector
hydroobject (writer GML2_2)
    attributes: code xml_buffer, naam xml_buffer, statusobjectcode xml_char(18), objectbegintijd xml_buffer, objecteindtijd xml_buffer, hyperlink xml_buffer, administratiefgebied xml_buffer, ruwheidstypecode xml_char(15), ruwheidswaardelaag xml_real64, ruwheidswaardehoog xml_real64
