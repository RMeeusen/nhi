FME workspace 20201002masterscript.fmw

Parameters:
- SourceDataset_ARCGIS_LAYER =
- SourceDataset_ARCGIS_LAYER_14 =
- SourceDataset_ARCGIS_LAYER_15 =
- SourceDataset_ARCGIS_LAYER_16 =
- SourceDataset_ARCGIS_LAYER_17 =
- SourceDataset_ARCGIS_LAYER_18 =
- SourceDataset_ARCGIS_LAYER_19 =
- SourceDataset_ARCGIS_LAYER_20 =
- SourceDataset_ARCGIS_LAYER_22 =
- SourceDataset_ARCGIS_LAYER_23 =
- SourceDataset_ARCGIS_LAYER_24 =
- SourceDataset_GEODATABASE_FILE =

Readers:
- ARCGIS_LAYER_1: ARCGIS_LAYER from $(SourceDataset_ARCGIS_LAYER)
- ARCGIS_LAYER_2: ARCGIS_LAYER from $(SourceDataset_ARCGIS_LAYER_17)
- ARCGIS_LAYER_3: ARCGIS_LAYER from $(SourceDataset_ARCGIS_LAYER_23)
- ARCGIS_LAYER_4: ARCGIS_LAYER from $(SourceDataset_ARCGIS_LAYER_22) in EPSG:28992
- ARCGIS_LAYER_5: ARCGIS_LAYER from $(SourceDataset_ARCGIS_LAYER_24) in EPSG:28992
- ARCGIS_LAYER_6: ARCGIS_LAYER from $(SourceDataset_ARCGIS_LAYER_15)
- ARCGIS_LAYER_7: ARCGIS_LAYER from $(SourceDataset_ARCGIS_LAYER_19)
- ARCGIS_LAYER_8: ARCGIS_LAYER from $(SourceDataset_ARCGIS_LAYER_14)
- ARCGIS_LAYER_9: ARCGIS_LAYER from $(SourceDataset_ARCGIS_LAYER_16)
- ARCGIS_LAYER_10: ARCGIS_LAYER from $(SourceDataset_ARCGIS_LAYER_18)
- ARCGIS_LAYER_11: ARCGIS_LAYER from $(SourceDataset_ARCGIS_LAYER_20)
- GEODATABASE_FILE_1: GEODATABASE_FILE from $(SourceDataset_GEODATABASE_FILE)

Note: KWKSTATU / 100 = planvorming / 201 = realisatie plan (lange termijn) / 202 = rp (middellange termijn) / 203 = rp (korte termijn) / 204 = rp (in uitvoering) / 300 = gerealiseerd / 400 = buiten bedrijf / gesloten / 500 = niet meer aanwezig / 9800 = onbekend / 9900 = overig

Bookmark: Inlezen data en voorbewerken data
BLAEU.GW_KDU (reader ARCGIS_LAYER_6)
    attributes: OBJECTID integer, KDUVORM integer, KDUHGA1 float, KDUHGA1_L float, KDUHGA2 float, KDUHGA2_L float, KDUBOKBO float, KDUBOKBO_L float, KDUBOKBE float, KDUBOKBE_L float, KDUBHBO float, KDUBHBE float, KDULENGT float, KDULENGT_L float, KDULNGGR float, KDUBREED float, KDUBREED_L float, KDUWAND float, KDUSLUIT float, KDUBUIS integer, KDUSTSK char(2), XXXMATER integer, KDUAFSBO integer, KDUAFSBE integer, KDUGRGEB char(2), KDUHVHGR float, KDUSOORT integer, IWS_HYPERLINK char(240), KEURVERGUNNING char(12), RISICO char(150),
      LBISTATG integer, KWKAFSL1 integer, KWKSTATU integer, KWKKERHG float, KWKKERHG_L float, KWKARCH char(100), KWKNAPH double, KWKNAPD date, KWKDATUM char(4), KWKOPME char(254), KWKPLAAN char(50), OSMOMSCH char(60), KWKAFSL2 integer, KWKAFSL3 integer, IWS_MEMO char(1073741822), KWKNAAM char(100), IWS_LEGGERSTATUS integer, IWS_STATUSTEKST char(1073741822), IWS_DATUM_LAATSTE_WIJZIGING date, IWS_OH_RENOVATIEJAAR integer, IWS_OH_AANLEGKOSTEN double, IWS_OH_LEVENSDUUR integer, IWS_OH_GRONDSOORT integer, IWS_OH_STATUS integer, IWS_OH_JAARH integer, IWS_OH_JAARB integer, KWK_X double, KWK_Y double, KDUIDENT char(24), RICHTING float,
      IWS_WATERBEHEERFUNCTIE integer, CREATED_USER char(50), CREATED_DATE date, LAST_EDITED_USER char(50), LAST_EDITED_DATE date, GEONAUWKEURIGHEID integer, ADMINNAUWKEURIGHEID integer, BETROUWBAARHEID integer, INWINNINGSWIJZE integer, INWINNINGSDATUM date, BRON char(255), IDEALISATIE integer, OPMERKINGEN char(255), GEONAUWKEURIGHEID_Z integer, IWS_KWLTGEO integer, KERIDENT char(30), GLOBALID char(2048), IWS_EIGENAAR char(255), LEG_ZIENSWIJZE integer, LEG_GEREED_VOOR_CL integer, IWS_EIGENAAR_K integer, IWS_AFST_B integer, IWS_ONDERDEEL_CALAMITEITENPLAN integer, IWS_OPSTAL_VERZEKERN integer, KDUMOEBE integer, KDUMOEBO integer, KWKKEREN integer, KWKCONT integer, SAMENSTELLINGINDICATOR integer, MIG_PSBR_KDU integer,
      SKK_SKK_ID char(2048), AMB_MUTATIE integer
    -> Tester_2
Note: Tester: status niet 100, 400 of 500
Tester_2
    BOOL_OP = COMPOSITE
    COMPOSITE_TEST = 1 AND 2 AND 3
    TEST_CLAUSE:
      TEST @Value(KWKSTATU) != 500
      TEST @Value(KWKSTATU) != 400
      TEST @Value(KWKSTATU) != 100
    TEST_MODE = TEST
    PASSED -> Tester_12
Note: Tester: moet valide code hebben (beginnen met "DR\d\d\d\d")
Tester_12
    BOOL_OP = AND
    COMPOSITE_TEST = 1 AND 2
    TEST_CLAUSE:
      CASE_INSENSITIVE_TEST @Value(KDUIDENT) BEGINS_WITH DR
      CASE_INSENSITIVE_TEST @Right(@Left(@Value(KDUIDENT),6),4) TYPE NUM
    TEST_MODE = CASE_INSENSITIVE_TEST
    PASSED -> Tester_11
Note: Maaipadduikers niet meenemen en Eigenaar Waterkeringen ook niet
Tester_11
    BOOL_OP = AND
    COMPOSITE_TEST = 1 AND 2
    TEST_CLAUSE:
      TEST @Value(KDUSOORT) != 1
      TEST @Value(IWS_EIGENAAR) != Waterkeringen
    TEST_MODE = TEST
    PASSED -> AttributeManager_9
AttributeManager_9
    ATTR_TABLE = RENAME_SET_VALUE GLOBALID > GLOBALID_KDU
    -> GeonisBlaeuToHyDAMOConverterDuikerSifonHevel [GeonisBlaeu_Duiker]
    -> GeonisBlaeuToHyDAMOConverterAfsluitmiddel [GeonisBlaeu_Duiker]
BLAEU.METINGPROFIELPUNT (reader ARCGIS_LAYER_5)
    attributes: OBJECTID integer, CODE char(50), SOORTMEETPUNT integer, TEKENCODE integer, CODEVOLGNUMMER integer, AFSTAND double, HOOGTE double, METINGPROFIELLIJNID guid, GLOBALID globalid
    -> AttributeManager_5
Note: Braces {} toevoegen aan METINGPROFIELLIJNID
AttributeManager_5
    ATTR_TABLE = SET_TO METINGPROFIELLIJNID = {@Value(METINGPROFIELLIJNID)}
    -> Tester_SOORTMEETPUNT
Tester_SOORTMEETPUNT
    BOOL_OP = OR
    COMPOSITE_TEST = 1 OR 2 OR 3
    TEST_CLAUSE:
      NUM_TEST @Value(SOORTMEETPUNT) RANGE [23,30]
      NUM_TEST @Value(SOORTMEETPUNT) RANGE [33,53]
      NUM_TEST @Value(SOORTMEETPUNT) RANGE [95,100]
    TEST_MODE = NUM_TEST
    PASSED -> AttributeManager_4
AttributeManager_4
    ATTR_TABLE:
      RENAME_SET_VALUE OBJECTID
      RENAME_SET_VALUE CODE > CODE_MPP
      RENAME_SET_VALUE GLOBALID > GLOBALID_MPP
    -> FeatureJoiner [LEFT]
BLAEU.METINGPROFIELLIJN (reader ARCGIS_LAYER_4)
    attributes: OBJECTID integer, CODE char(50), SOORTPROFIEL integer, PROFIELWEERGAVE integer, DATUMTIJDINWINNING date, STATUS integer, REFERENTIEVLAK char(2), OPMERKING char(500), NAAMSPACE char(50), LOKAALID char(50), BERGINGSGEBIEDID guid, HYDROOBJECTID guid, WATERKERINGID guid, METADATAID integer, METINGPROFIELLIJNID guid, GLOBALID globalid, CREATED_USER char(255), CREATED_DATE date, LAST_EDITED_USER char(255), LAST_EDITED_DATE date, PROFIELREEKSID guid, WRIJ_REEKSIDENT char(24), WRIJ_REEKSOMSCH char(100), SHAPE.LEN double
    -> AttributeFilter_2
Note: PROFIELWEERGAVE / 1 = Gemeten: Vaste bodem / 2 = Gemeten: Modderlaag
AttributeFilter_2
    ATTR_NAME = PROFIELWEERGAVE
    ATTR_VALUES = <Empty>,<Missing>,<Null>,<Unfiltered>,1,2
    1 -> AttributeFilter
    2 -> AttributeFilter
Note: SOORTPROFIEL / 2 = Dwarsprof. Waterkering / 7 = PROF. / 11 = Profiel gemeten over kunstwerk
AttributeFilter
    ATTR_NAME = SOORTPROFIEL
    ATTR_VALUES = <Empty>,<Missing>,<Null>,<Unfiltered>,7,11,2
    7 -> AttributeManager_3
    11 -> AttributeManager_6
    11 -> AttributeManager_3
    2 -> AttributeManager_3
AttributeManager_3
    ATTR_TABLE:
      RENAME_SET_VALUE OBJECTID
      RENAME_SET_VALUE CODE > CODE_MPL
      RENAME_SET_VALUE STATUS > STATUS_MPL
      REMOVE REFERENTIEVLAK
      REMOVE OPMERKING
      REMOVE NAAMSPACE
      REMOVE LOKAALID
      SET_TO HYDROOBJECTID = {@Value(HYDROOBJECTID)}
      REMOVE METADATAID
      REMOVE METINGPROFIELLIJNID
      RENAME_SET_VALUE GLOBALID > GLOBALID_MPL
      REMOVE CREATED_USER
      RENAME_SET_VALUE CREATED_DATE > CREATED_DATE_MPL
      REMOVE LAST_EDITED_USER
      RENAME_SET_VALUE LAST_EDITED_DATE > LAST_EDITED_DATE_MPL
    -> FeatureJoiner_2 [LEFT]
    -> FeatureJoiner [RIGHT]
Note: Overhalen data van MetingProfielLijn
FeatureJoiner
    ATTR_CONFLICT_RES = Use Left
    GEOMETRY_HANDLING = Use Left
    JOIN_KEYS = METINGPROFIELLIJNID GLOBALID_MPL AUTO
    JOIN_MODE = Inner
    JOINED -> GeonisBlaeuToHyDAMOConverterMetingProfiel [GeonisBlaeu_DwarsprofielGemeten_punten]
AttributeManager_6
    ATTR_TABLE:
      RENAME_SET_VALUE OBJECTID > OBJECTID_MPL
      RENAME_SET_VALUE CODE > CODE_MPL
      RENAME_SET_VALUE STATUS > STATUS_MPL
      REMOVE REFERENTIEVLAK
      REMOVE OPMERKING
      REMOVE NAAMSPACE
      REMOVE LOKAALID
      SET_TO HYDROOBJECTID = {@Value(HYDROOBJECTID)}
      REMOVE WATERKERINGID
      REMOVE METADATAID
      REMOVE METINGPROFIELLIJNID
      RENAME_SET_VALUE GLOBALID > GLOBALID_MPL
      REMOVE CREATED_USER
      RENAME_SET_VALUE CREATED_DATE > CREATED_DATE_MPL
      REMOVE LAST_EDITED_USER
      RENAME_SET_VALUE LAST_EDITED_DATE > LAST_EDITED_DATE_MPL
    -> SpatialFilter [Candidate]
BLAEU.GW_OVK (reader ARCGIS_LAYER_1)
    attributes: AARD char(3), ADMINNAUWKEURIGHEID integer, AMB_MUTATIE integer, AVVBERMT integer, AVVBODDR float, AVVBODH float, AVVDIEPT float, AVVDROOB integer, AVVDROOE integer, AVVGEMBH float, AVVHOBES float, AVVHOBOS float, AVVHYDST float, AVVKNKL_L float, AVVKNKL2_L float, AVVKNKR_L float, AVVKNKR2_L float, AVVNATOM float, AVVNATOP float, AVVSNELH float, AVVTALL2_L float, AVVTALR2_L float, AVVTALUL float, AVVTALUR float, AVVVERHG float, AVVWNTPL float, AVVWRHFC float, AVVZMRPL float, BAGCYCL integer, BAGGERTRANSPORT integer,
      BETROUWBAARHEID integer, BOH_MUT_JAAR integer, BOHINR_BIJZ_LNG double, BOHINR_BIJZ_TXT char(50), BOHINR_JJEVEN integer, BOHINR_JJONEVEN integer, BOHINR_STATUS integer, BOHINR_TYPE integer, BRON char(255), COMBITYPE_KRW_VISMIG_NTW integer, CREATED_DATE date, CREATED_USER char(50), GEB_FUNCTIE char(2), GEONAUWKEURIGHEID integer, GEONAUWKEURIGHEID_Z integer, GLOBALID char(2048), IDEALISATIE integer, INWINNINGSDATUM date, INWINNINGSWIJZE integer, IWS_AVVHOBES_L float, IWS_AVVHOBOS_L float, IWS_BEGIN_AFSTAND integer, IWS_BESCHZONEBI float, IWS_BESCHZONEBU float, IWS_BOV_BR integer, IWS_BOVENBREEDTE_KANT_INSTEEK float, IWS_BREEDTE float, IWS_CATEGORIEEN integer, IWS_CLASSIFICATIE_WATERVOERING integer, IWS_EIGENAAR char(255),
      IWS_EIND_AFSTAND integer, IWS_GEOGRAFLIGGING integer, IWS_KWLTGEO integer, IWS_LEGGERSTATUS integer, IWS_LENGTE double, IWS_MAAIVELD_BENEDENSTROOMS float, IWS_MAAIVELD_BOVENSTROOMS float, IWS_MEMO char(2000), IWS_OWASRTKN integer, IWS_STATUSTEKST char(2000), IWS_TOEGANKELIJK integer, IWS_VAKTYPE integer, IWS_W_BRPLASBL float, IWS_W_BRPLASBR float, IWS_W_INSTHGTEL float, IWS_W_INSTHGTER float, IWS_W_PLASBH_DL float, IWS_W_PLASBH_DR float, IWS_W_PLASBTALL float, IWS_W_PLASBTALR float, IWS_W_REFPEIL integer, IWS_W_WATBRREFP float, IWS_W_WATPEIL float, IWS_ZSTRAF integer, IWS_ZSTRAN integer, KWKSTATU integer, LAST_EDITED_DATE date, LAST_EDITED_USER char(50), LEG_GEREED_VOOR_CL integer, LEG_ZIENSWIJZE integer,
      MIGRTYPE_KRW_VISMIG_NTW integer, MOH_MUT_JAAR integer, MOHINR_BIJZ_LNG double, MOHINR_BIJZ_TXT char(50), MOHINR_JJEVEN integer, MOHINR_JJONEVEN integer, MOHINR_STATUS integer, NETWERK_ECOLOGIE integer, NETWERK_KRW_VISMIGRATIE integer, OBJECTID integer, OH_BAGGERPL char(50), OH_PAKKET char(6), OH_PAKKET_BASIS char(6), OHBLD_P1 integer, OHBLD_P2 integer, OHBLD_P3 integer, OHBLD_P4 integer, OHINR_TYPE integer, OPMERKINGEN char(255), OSMOMSCH char(60), OVK_TYPE char(10), OVKIDENT char(24), OVKLENGT integer, OVKSOORT integer, OWA_OWA_ID char(2048), OWM_OWM_ID char(2048), QSCAN_BLD_DATE char(10), QSCAN_BLD_TOETS integer, RICHTING float, STEDELIJK_WATER_OVK integer,
      STR_BLD_CODE integer, STR_BLD_DATE char(10), STR_BLD_OPMERK char(50), WRIJ_AFVOER_CUMULATIEF double, WRIJ_AFVOER_EXTERN_OPGELEGD integer, WRIJ_AFVOER_HYDROVAK double, WRIJ_AVVKNKL_L_BE double, WRIJ_AVVKNKL2_L_BE double, WRIJ_AVVKNKR_L_BE double, WRIJ_AVVKNKR2_L_BE double, WRIJ_IWS_W_PLASBH_DL_BE double, WRIJ_IWS_W_PLASBH_DR_BE double
    -> LengthCalculator
LengthCalculator
    DIM = 2
    LEN_ATTR = SHAPE.LEN
    MULT = 1
    -> AttributeManager_8
AttributeManager_8
    ATTR_TABLE = RENAME_SET_VALUE GLOBALID > GLOBALID_LV
    -> Tester_9
Note: Tester: status niet 100, 400 of 500
Tester_9
    BOOL_OP = AND
    TEST_CLAUSE:
      TEST @Value(KWKSTATU) != 500
      TEST @Value(KWKSTATU) != 400
      TEST @Value(KWKSTATU) != 100
    TEST_MODE = TEST
    PASSED -> GeonisBlaeuToHyDAMOConverterHydroobject [GeonisBlaeu_Leidingvakken]
    PASSED -> FeatureJoiner_2 [RIGHT]
    PASSED -> GeonisBlaeuToHyDAMOConverterMetingProfiel [GeonisBlaeu_Leidingvak_met_leggerprofielen]
Note: Ophalen OVKIDENT obv GLOBALID_LV
FeatureJoiner_2
    ATTR_CONFLICT_RES = Use Left
    GEOMETRY_HANDLING = Use Left
    JOIN_KEYS = HYDROOBJECTID GLOBALID_LV AUTO
    JOIN_MODE = Inner
    JOINED -> GeonisBlaeuToHyDAMOConverterMetingProfiel [GeonisBlaeu_DwarsprofielGemeten_lijnen]
BLAEU.GW_OWA (reader ARCGIS_LAYER_2)
    attributes: OBJECTID integer, OWA_TYPE char(10), OWAIDENT char(24), OWLBODHO float, LBISTATG integer, OWABERGW double, OWABERGZ double, OWANAAM char(50), OWASRTKN integer, OWASRTKL integer, OWACATEG integer, OWAINOOR integer, OWALENGT integer, OWADATVL date, OWAWATST float, OWAOPPVL integer, OWAVOLUM double, OWAINLAA float, OWAAFLAA float, OWASTRAF integer, OWASTRAN integer, OWAOPME char(50), OWASRTVO integer, OWAFUNC1 integer, OWAFUNC2 integer, OWAFUNC3 integer, IWS_MEMO char(2000), IOTW_CODE char(24), OWAFUNCT char(6), IWS_DIEPSTE_PUNT char(10),
      IWS_GEM_BODHO_VLAKTE float, IWS_STATUS integer, IWS_LEGGERSTATUS integer, IWS_STATUSTEKST char(2000), WGBIDENT char(24), OWARIJK integer, OWANIVO char(10), OWAJAAR integer, IWS_BOUWJAAR integer, RICHTING float, CREATED_USER char(50), CREATED_DATE date, LAST_EDITED_USER char(50), LAST_EDITED_DATE date, GEONAUWKEURIGHEID integer, ADMINNAUWKEURIGHEID integer, BETROUWBAARHEID integer, INWINNINGSWIJZE integer, INWINNINGSDATUM date, BRON char(255), IDEALISATIE integer, OPMERKINGEN char(255), GEONAUWKEURIGHEID_Z integer, IWS_KWLTGEO integer, IWS_EIGENAAR char(255), GLOBALID char(2048), STEDELIJK_WATER_OWA integer, OWASGCAT integer, WBHCODE integer, OWM_OWM_ID char(2048)
    -> AttributeCreator_OWA_2
AttributeCreator_OWA_2
    ATTR_TABLE = SET_TO OWANAAM = FME_CONDITIONAL:DEFAULT_VALUE'_FME_NO_OP_'BOOL_OP;OR;COMPOSITE_TEST;<Unused>;TEST OWANAAM ATTRIBUTE_VALUE_NULL _FME_BLANK_STRING_'NoName'FME_NUM_CONDITIONS2___
    -> Tester_10
Note: Tester: status niet 100, 400 of 500
Tester_10
    BOOL_OP = COMPOSITE
    COMPOSITE_TEST = 1 AND 2 AND 3
    TEST_CLAUSE:
      TEST @Value(IWS_STATUS) != 500
      TEST @Value(IWS_STATUS) != 400
      TEST @Value(IWS_STATUS) != 100
    TEST_MODE = TEST
    PASSED -> GeonisBlaeuToHyDAMOConverterHydroobject [GeonisBlaeuWaterlopen]
BLAEU.GW_KST (reader ARCGIS_LAYER_3)
    attributes: OBJECTID integer, KSTSOORT integer, KSTHOOGT float, KSTMIKHO float, KSTMAXBR_L float, KSTMAXKR float, KSTDSBRE float, KSTDSBRE_L float, KSTKRUBR float, KSTKRUBR_L float, KSTLENGT float, KSTKRLEN float, KSTKRLEN_L float, KSTKRVRM integer, KSTPEIL float, KSTAANT integer, KSTMATRC integer, KSTMATHC integer, KSTSRTBW integer, KSTSOOR1 integer, KSTREGEL integer, KSTKRUHO float, KSTKRUHO_L float, KSTMIKHO_L float, IWS_KSTZMRPL float, IWS_KSTWTPL float, IWS_HYPERLINK char(240), KEURVERGUNNING char(12), RISICO char(150), LBISTATG integer,
      KWKAFSL1 integer, KWKSTATU integer, KWKKERHG float, KWKKERHG_L float, KWKARCH char(100), KWKNAPH double, KWKNAPD date, KWKDATUM char(4), KWKOPME char(254), KWKPLAAN char(50), OSMOMSCH char(60), KWKAFSL2 integer, KWKAFSL3 integer, IWS_MEMO char(1073741822), KWKNAAM char(100), IWS_LEGGERSTATUS integer, IWS_STATUSTEKST char(1073741822), IWS_ELECTROTECHNISCH double, IWS_DATUM_LAATSTE_WIJZIGING date, IWS_EEG_OPMERKINGEN char(240), IWS_OH_RENOVATIEJAAR integer, IWS_OH_AANLEGKOSTEN double, IWS_OH_LEVENSDUUR integer, IWS_OH_GRONDSOORT integer, IWS_OH_STATUS integer, IWS_OH_JAARH integer, IWS_OH_JAARB integer, IWS_OH_KOSTENH double, KWK_X double, KWK_Y double,
      KSTIDENT char(24), RICHTING float, CREATED_DATE date, LAST_EDITED_DATE date, CREATED_USER char(30), LAST_EDITED_USER char(30), IWS_WATERBEHEERFUNCTIE integer, GEONAUWKEURIGHEID integer, ADMINNAUWKEURIGHEID integer, BETROUWBAARHEID integer, INWINNINGSWIJZE integer, INWINNINGSDATUM date, BRON char(255), IDEALISATIE integer, OPMERKINGEN char(255), GEONAUWKEURIGHEID_Z integer, IWS_KWLTGEO integer, KERIDENT char(30), GLOBALID char(2048), IWS_EIGENAAR char(255), LEG_ZIENSWIJZE integer, LEG_GEREED_VOOR_CL integer, IWS_EIGENAAR_K integer, IWS_AFST_B integer, IWS_ONDERDEEL_CALAMITEITENPLAN integer, KWKKEREN integer, KWKCONT integer, IND_MEETSTUW integer, KSTLUCHT integer, SAMENSTELLINGINDICATOR integer,
      MIG_PSBR_KST integer, SKK_SKK_ID char(2048), AMB_MUTATIE integer
    -> Tester
Note: Tester: status niet 500 en niet in duitsland
Tester
    BOOL_OP = COMPOSITE
    COMPOSITE_TEST = 1 AND 2
    TEST_CLAUSE:
      TEST @Value(KWKSTATU) != 500
      TEST @Value(IWS_LEGGERSTATUS) IN 1,2
    TEST_MODE = TEST
    PASSED -> AttributeManager
Note: Correctie op Doorstroombreedte en Kruinbreedte: bij ontbreken gebruik de andere waarde en bij verkeerde invulling wissel de uitkomst om. / Aantal stuwen: lege cellen krijgen waarde 1. Indien aantal >1 EN soort = 5-cascadestuw, dan is het waarschijnlijk een vistrap dus aantal = 1.
AttributeManager
    ATTR_TABLE:
      SET_TO KSTHOOGT_origineel = @Value(KSTHOOGT)
      SET_TO KSTDSBRE_origineel = @Value(KSTDSBRE)
      SET_TO KSTKRUBR_origineel = @Value(KSTKRUBR)
      SET_TO KSTHOOGT = FME_CONDITIONAL:DEFAULT_VALUE'_FME_NO_OP_'BOOL_OP;OR;COMPOSITE_TEST;<Unused>;TEST KSTHOOGT_origineel NOT_ATTRIBUTE_HAS_A_VALUE _FME_BLANK_STRING_'@Value(KSTMAXKR)'BOOL_OP;OR;COMPOSITE_TEST;<Unused>;TEST @Value(KSTHOOGT_origineel) < @Value(KSTMAXKR)'@Value(KSTMAXKR)'FME_NUM_CONDITIONS3___
      SET_TO KSTDSBRE = FME_CONDITIONAL:DEFAULT_VALUE'_FME_NO_OP_'BOOL_OP;OR;COMPOSITE_TEST;<Unused>;TEST KSTDSBRE_origineel NOT_ATTRIBUTE_HAS_A_VALUE _FME_BLANK_STRING_'@Value(KSTKRUBR_origineel)'BOOL_OP;AND;COMPOSITE_TEST;<Unused>;TEST KSTDSBRE_origineel ATTRIBUTE_HAS_A_VALUE _FME_BLANK_STRING_;TEST KSTKRUBR_origineel ATTRIBUTE_HAS_A_VALUE _FME_BLANK_STRING_;TEST @Value(KSTDSBRE_origineel) > @Value(KSTKRUBR_origineel)'@Value(KSTKRUBR_origineel)'FME_NUM_CONDITIONS3___
      SET_TO KSTKRUBR = FME_CONDITIONAL:DEFAULT_VALUE'_FME_NO_OP_'BOOL_OP;OR;COMPOSITE_TEST;<Unused>;TEST KSTKRUBR_origineel NOT_ATTRIBUTE_HAS_A_VALUE _FME_BLANK_STRING_'@Value(KSTDSBRE_origineel)'BOOL_OP;AND;COMPOSITE_TEST;<Unused>;TEST KSTDSBRE_origineel ATTRIBUTE_HAS_A_VALUE _FME_BLANK_STRING_;TEST KSTKRUBR_origineel ATTRIBUTE_HAS_A_VALUE _FME_BLANK_STRING_;TEST @Value(KSTDSBRE_origineel) > @Value(KSTKRUBR_origineel)'@Value(KSTDSBRE_origineel)'FME_NUM_CONDITIONS3___
      SET_TO KSTAANT = FME_CONDITIONAL:DEFAULT_VALUE'@Value(KSTAANT)'BOOL_OP;OR;COMPOSITE_TEST;1;TEST KSTAANT ATTRIBUTE_VALUE_NULL _FME_BLANK_STRING_'1'BOOL_OP;AND;COMPOSITE_TEST;1 AND 2;TEST @Value(KSTAANT) > 1;TEST @Value(KSTSOORT) = 5'1'FME_NUM_CONDITIONS3___
      RENAME_SET_VALUE GLOBALID > GLOBALID_KST
    -> GeonisBlaeuToHyDAMOConverterStuw [GeonisBlaeu_Stuw]
    -> AttributeManager_7
AttributeManager_7
    ATTR_TABLE:
      REMOVE KSTHOOGT_origineel
      REMOVE KSTDSBRE_origineel
      REMOVE KSTKRUBR_origineel
      REMOVE OBJECTID
      REMOVE KSTSOORT
      REMOVE KSTHOOGT
      REMOVE KSTMIKHO
      REMOVE KSTMAXBR_L
      REMOVE KSTMAXKR
      REMOVE KSTDSBRE
      REMOVE KSTDSBRE_L
      REMOVE KSTKRUBR
      REMOVE KSTKRUBR_L
      REMOVE KSTLENGT
      REMOVE KSTKRLEN
      REMOVE KSTKRLEN_L
      REMOVE KSTKRVRM
      REMOVE KSTPEIL
      REMOVE KSTAANT
      REMOVE KSTMATRC
      REMOVE KSTMATHC
      REMOVE KSTSRTBW
      REMOVE KSTSOOR1
      REMOVE KSTREGEL
      REMOVE KSTKRUHO
      REMOVE KSTKRUHO_L
      REMOVE KSTMIKHO_L
      REMOVE IWS_KSTZMRPL
      REMOVE IWS_KSTWTPL
      REMOVE IWS_HYPERLINK
      REMOVE KEURVERGUNNING
      REMOVE RISICO
      REMOVE LBISTATG
      REMOVE KWKAFSL1
      REMOVE KWKSTATU
      REMOVE KWKKERHG
      REMOVE KWKKERHG_L
      REMOVE KWKARCH
      REMOVE KWKNAPH
      REMOVE KWKNAPD
      REMOVE KWKDATUM
      REMOVE KWKOPME
      REMOVE KWKPLAAN
      REMOVE OSMOMSCH
      REMOVE KWKAFSL2
      REMOVE KWKAFSL3
      REMOVE IWS_MEMO
      REMOVE KWKNAAM
      REMOVE IWS_LEGGERSTATUS
      REMOVE IWS_STATUSTEKST
      REMOVE IWS_ELECTROTECHNISCH
      REMOVE IWS_DATUM_LAATSTE_WIJZIGING
      REMOVE IWS_EEG_OPMERKINGEN
      REMOVE IWS_OH_RENOVATIEJAAR
      REMOVE IWS_OH_AANLEGKOSTEN
      REMOVE IWS_OH_LEVENSDUUR
      REMOVE IWS_OH_GRONDSOORT
      REMOVE IWS_OH_STATUS
      REMOVE IWS_OH_JAARH
      REMOVE IWS_OH_JAARB
      REMOVE IWS_OH_KOSTENH
      REMOVE KWK_X
      REMOVE KWK_Y
      REMOVE RICHTING
      REMOVE CREATED_DATE
      REMOVE LAST_EDITED_DATE
      REMOVE CREATED_USER
      REMOVE LAST_EDITED_USER
      REMOVE IWS_WATERBEHEERFUNCTIE
      REMOVE GEONAUWKEURIGHEID
      REMOVE ADMINNAUWKEURIGHEID
      REMOVE BETROUWBAARHEID
      REMOVE INWINNINGSWIJZE
      REMOVE INWINNINGSDATUM
      REMOVE BRON
      REMOVE IDEALISATIE
      REMOVE OPMERKINGEN
      REMOVE GEONAUWKEURIGHEID_Z
      REMOVE IWS_KWLTGEO
      REMOVE KERIDENT
      REMOVE IWS_EIGENAAR
      REMOVE LEG_ZIENSWIJZE
      REMOVE LEG_GEREED_VOOR_CL
      REMOVE IWS_EIGENAAR_K
      REMOVE IWS_AFST_B
      REMOVE IWS_ONDERDEEL_CALAMITEITENPLAN
      REMOVE KWKKEREN
      REMOVE KWKCONT
      REMOVE IND_MEETSTUW
      REMOVE KSTLUCHT
      REMOVE SAMENSTELLINGINDICATOR
      REMOVE MIG_PSBR_KST
      REMOVE SKK_SKK_ID
      REMOVE AMB_MUTATIE
    -> Bufferer5m
Bufferer5m
    ANGLE = 5
    CAP_STYLE = Round
    CORNER_STYLE = Round
    MODE = AREA
    OFFSET = 5
    OFFSET_UNITS = METERS
    PRECISION = APPROX
    BUFFERED -> SpatialFilter [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> GeonisBlaeuToHyDAMOConverterMetingProfiel [GeonisBlaeu_DwarsprofielGemeten_lijnen]
BLAEU.GW_AKN (reader ARCGIS_LAYER_7)
    attributes: OBJECTID integer, KWKIDENT char(24), LBISTATG integer, KWKGEOM1 integer, KWKAFSL1 integer, KWKSTATU integer, KWKKERHG float, KWKKERHG_L float, KWKARCH char(100), KWKNAPH double, KWKDATUM char(4), KWKOPME char(50), KWKPLAAN char(50), OSMOMSCH char(60), KWKAFSL2 integer, KWKAFSL3 integer, KEURVERGUNNING char(12), RISICO char(150), KWKNAPD date, IWS_LEGGERSTATUS integer, IWS_STATUSTEKST char(1073741822), IWS_MEMO char(1073741822), KWKNAAM char(60), IWS_DATUM_LAATSTE_WIJZIGING date, IWS_HYPERLINK char(240), IWS_OH_RENOVATIEJAAR integer, IWS_OH_AANLEGKOSTEN double, IWS_OH_LEVENSDUUR integer, IWS_OH_GRONDSOORT integer, IWS_OH_STATUS integer,
      IWS_OH_JAARH integer, IWS_OH_JAARB integer, IWS_OH_KOSTENH double, KWK_X double, KWK_Y double, KWKCONT char(1), RICHTING float, IWS_ONDERDEEL_CALAMITEITENPLAN char(1), IWS_WATERBEHEERFUNCTIE integer, CREATED_USER char(50), CREATED_DATE date, LAST_EDITED_USER char(50), LAST_EDITED_DATE date, GEONAUWKEURIGHEID integer, ADMINNAUWKEURIGHEID integer, BETROUWBAARHEID integer, INWINNINGSWIJZE integer, INWINNINGSDATUM date, BRON char(255), IDEALISATIE integer, OPMERKINGEN char(255), GEONAUWKEURIGHEID_Z integer, IWS_KWLTGEO integer, KERIDENT char(30), GLOBALID char(2048), IWS_EIGENAAR char(255), IWS_EIGENAAR_K integer, IWS_AFST_B integer, KWKKEREN integer, SAMENSTELLINGINDICATOR integer,
      SKK_SKK_ID char(2048), KWK_KWK_ID char(2048), OWM_OWM_ID char(2048), WRIJ_TYPE_REGELBAARHEID integer, WRIJ_PRIMAIRE_BEDIENING integer, WRIJ_SECUNDAIRE_BEDIENING integer, WRIJ_FUNCTIE integer, WRIJ_BEDRIJFSTOESTAND integer, WRIJ_ACTIE_HOOGWATER integer, WRIJ_MAATGEVENDE_WATERSTAND float, WRIJ_LIGGING integer, WRIJ_STATUS_ONDERHOUD char(50), WRIJ_VERWERKING_GEO char(50), LEG_ZIENSWIJZE integer, LEG_GEREED_VOOR_CL integer, AMB_MUTATIE integer
    -> Tester_3
Note: Tester: status niet 100, 400 of 500
Tester_3
    BOOL_OP = COMPOSITE
    COMPOSITE_TEST = 1 AND 2 AND 3
    TEST_CLAUSE:
      TEST @Value(KWKSTATU) != 500
      TEST @Value(KWKSTATU) != 400
      TEST @Value(KWKSTATU) != 100
    TEST_MODE = TEST
    PASSED -> Tester_8
Note: Tester: moet valide code hebben (beginnen met "AF")
Tester_8
    BOOL_OP = OR
    COMPOSITE_TEST = 1
    TEST_CLAUSE = CASE_INSENSITIVE_TEST @Value(KWKIDENT) BEGINS_WITH AF
    TEST_MODE = TEST
    PASSED -> AttributeManager_10
AttributeManager_10
    ATTR_TABLE = RENAME_SET_VALUE GLOBALID > GLOBALID_AKN
    -> GeonisBlaeuToHyDAMOConverterAfsluitmiddel [GeonisBlaeu_Afsluiter]
BLAEU.GW_KGM (reader ARCGIS_LAYER_8)
    attributes: OBJECTID integer, KGMSOORT integer, KGMAANDR integer, KGMAAPOM integer, KGMMACAP double, KGMMACAP_L double, KGMSLUIT float, KGMSLUIT_L float, KPGAANSD float, KPGAANSN float, KGMFUNC integer, IWS_COMCAP double, IWS_HYPERLINK char(240), KEURVERGUNNING char(12), RISICO char(150), LBISTATG integer, KWKAFSL1 integer, KWKSTATU integer, KWKKERHG float, KWKKERHG_L float, KWKARCH char(100), KWKNAPH double, KWKNAPD date, KWKDATUM char(4), KWKOPME char(254), KWKPLAAN char(50), OSMOMSCH char(60), KWKAFSL2 integer, KWKAFSL3 integer, IWS_MEMO char(1073741822),
      KWKNAAM char(100), IWS_LEGGERSTATUS integer, IWS_STATUSTEKST char(1073741822), IWS_ELECTROTECHNISCH double, IWS_DATUM_LAATSTE_WIJZIGING date, IWS_OH_RENOVATIEJAAR integer, IWS_OH_LEVENSDUUR integer, IWS_OH_JAARH integer, IWS_OH_JAARB integer, KWK_X double, KWK_Y double, KGMIDENT char(24), RICHTING float, IWS_WATERBEHEERFUNCTIE integer, CREATED_USER char(50), CREATED_DATE date, LAST_EDITED_USER char(50), LAST_EDITED_DATE date, GEONAUWKEURIGHEID integer, ADMINNAUWKEURIGHEID integer, BETROUWBAARHEID integer, INWINNINGSWIJZE integer, INWINNINGSDATUM date, BRON char(255), IDEALISATIE integer, OPMERKINGEN char(255), GEONAUWKEURIGHEID_Z integer, IWS_KWLTGEO integer, KERIDENT char(30), GLOBALID char(2048),
      IWS_EIGENAAR char(255), LEG_ZIENSWIJZE integer, LEG_GEREED_VOOR_CL integer, IWS_EIGENAAR_K integer, IWS_AFST_B integer, IWS_ONDERDEEL_CALAMITEITENPLAN integer, KWKINLAT integer, KWKKEREN integer, KWKCONT integer, SAMENSTELLINGINDICATOR integer, MIG_PSBR_KGM integer, SKK_SKK_ID char(2048), AMB_MUTATIE integer
    -> Tester_4
Note: Tester: status niet 500
Tester_4
    BOOL_OP = AND
    TEST_CLAUSE = TEST @Value(KWKSTATU) != 500
    TEST_MODE = TEST
    PASSED -> AttributeManager_2
Note: Aantal gemalen; lege cellen op 1 zetten indien niet ingevuld
AttributeManager_2
    ATTR_TABLE:
      RENAME_SET_VALUE GLOBALID > GLOBALID_KGM
      SET_TO KGMAAPOM = FME_CONDITIONAL:DEFAULT_VALUE'1'BOOL_OP;OR;COMPOSITE_TEST;<Unused>;TEST KGMAAPOM ATTRIBUTE_HAS_A_VALUE _FME_BLANK_STRING_'_FME_NO_OP_'FME_NUM_CONDITIONS2___
    -> GeonisBlaeuToHyDAMOConverterPomp [GeonisBlaeu_Gemaal]
BLAEU.GW_KBR (reader ARCGIS_LAYER_9)
    attributes: OBJECTID integer, KBRSOORT integer, KBRHOBB float, KBRBHBO float, KBRBHBO_L float, KBRBHBE float, KBRBHBE_L float, KBRHOBO float, KBRHOBO_L float, KBRHOBE float, KBRHOBE_L float, KBRBREED float, KBRLENGT float, KBRLAAG float, KBRMATBD integer, KDUMATDC integer, KBRMATPY integer, KBRMATLH integer, KBRMATLE integer, KBRHOEK float, KBRINDVK integer, KBRMARIK integer, KHAREFVL integer, KBRAANTD integer, KBRBTYPE integer, KBRDONUM integer, KBRWIJD float, KBRWIJD_L float, KBRHOPEN float, KBRHGESL float,
      KBRBESRT integer, IWS_AANTAL_PIJLERS integer, KEURVERGUNNING char(12), RISICO char(150), LBISTATG integer, KWKAFSL1 integer, KWKSTATU integer, KWKKERHG float, KWKKERHG_L float, KWKARCH char(100), KWKNAPH double, KWKNAPD date, KWKDATUM char(4), KWKOPME char(254), KWKPLAAN char(50), OSMOMSCH char(60), KWKAFSL2 integer, KWKAFSL3 integer, IWS_MEMO char(1073741822), KWKNAAM char(100), IWS_LEGGERSTATUS integer, IWS_STATUSTEKST char(1073741822), IWS_DATUM_LAATSTE_WIJZIGING date, IWS_OH_RENOVATIEJAAR integer, KWK_X double, KWK_Y double, KBRIDENT char(24), RICHTING float, IWS_WATERBEHEERFUNCTIE integer, CREATED_USER char(50),
      CREATED_DATE date, LAST_EDITED_USER char(50), LAST_EDITED_DATE date, GEONAUWKEURIGHEID integer, ADMINNAUWKEURIGHEID integer, BETROUWBAARHEID integer, INWINNINGSWIJZE integer, INWINNINGSDATUM date, BRON char(255), IDEALISATIE integer, OPMERKINGEN char(255), GEONAUWKEURIGHEID_Z integer, IWS_KWLTGEO integer, KERIDENT char(30), GLOBALID char(2048), IWS_EIGENAAR char(255), IWS_EIGENAAR_K integer, IWS_AFST_B integer, IWS_ONDERDEEL_CALAMITEITENPLAN integer, KBRBDIEN integer, KBRBEWEG integer, KBRSCAN integer, KWKKEREN integer, KWKCONT integer, SAMENSTELLINGINDICATOR integer, SKK_SKK_ID char(2048), LEG_ZIENSWIJZE integer, LEG_GEREED_VOOR_CL integer, AMB_MUTATIE integer
    -> Tester_5
Note: Tester: status niet 500
Tester_5
    BOOL_OP = OR
    COMPOSITE_TEST = 1
    TEST_CLAUSE = TEST @Value(KWKSTATU) != 500
    TEST_MODE = TEST
    PASSED -> AttributeManager_11
AttributeManager_11
    ATTR_TABLE = RENAME_SET_VALUE GLOBALID > GLOBALID_KBR
    -> GeonisBlaeuToHyDAMOConverterBrug [GeonisBlaeu_Brug]
BLAEU.GW_KBV (reader ARCGIS_LAYER_10)
    attributes: OBJECTID integer, KBVSOORT integer, KBVHOBO float, KBVHOBO_L float, KBVHOBE float, KBVHOBE_L float, KBVBREED float, KBVBREED_L float, KBVLENGT float, XXXMATER integer, KEURVERGUNNING char(12), RISICO char(150), LBISTATG integer, KWKAFSL1 integer, KWKSTATU integer, KWKKERHG float, KWKKERHG_L float, KWKARCH char(100), KWKNAPH double, KWKNAPD date, KWKDATUM char(4), KWKOPME char(254), KWKPLAAN char(50), OSMOMSCH char(60), KWKAFSL2 integer, KWKAFSL3 integer, IWS_MEMO char(1073741822), KWKNAAM char(100), IWS_LEGGERSTATUS integer, IWS_STATUSTEKST char(1073741822),
      IWS_DATUM_LAATSTE_WIJZIGING date, KWK_X double, KWK_Y double, KBVIDENT char(24), RICHTING float, IWS_WATERBEHEERFUNCTIE integer, CREATED_USER char(50), CREATED_DATE date, LAST_EDITED_USER char(50), LAST_EDITED_DATE date, GEONAUWKEURIGHEID integer, ADMINNAUWKEURIGHEID integer, BETROUWBAARHEID integer, INWINNINGSWIJZE integer, INWINNINGSDATUM date, BRON char(255), IDEALISATIE integer, OPMERKINGEN char(255), GEONAUWKEURIGHEID_Z integer, IWS_KWLTGEO integer, GLOBALID char(2048), IWS_EIGENAAR char(255), LEG_ZIENSWIJZE integer, LEG_GEREED_VOOR_CL integer, IWS_EIGENAAR_K integer, IWS_AFST_B integer, IWS_ONDERDEEL_CALAMITEITENPLAN integer, KWKKEREN integer, KWKCONT integer, SAMENSTELLINGINDICATOR integer,
      MIG_PSBR_KBV integer, SKK_SKK_ID char(2048), AMB_MUTATIE integer
    -> Tester_6
Note: Tester: status niet 500
Tester_6
    BOOL_OP = OR
    COMPOSITE_TEST = 1
    TEST_CLAUSE = TEST @Value(KWKSTATU) != 500
    TEST_MODE = TEST
    PASSED -> AttributeManager_12
AttributeManager_12
    ATTR_TABLE = RENAME_SET_VALUE GLOBALID > GLOBALID_KBV
    -> GeonisBlaeuToHyDAMOConverterBodemval [GeonisBlaeu_Bodemval]
MeetlocatiesHydrologie (reader GEODATABASE_FILE_1) [off]
    attributes: OBJECTID_1 integer, OBJECTID integer, SITE_TYPE char(50), SITE_NAME char(75), SITE_NO char(100), X_COORD double, Y_COORD double, LOKID integer, LOKID_CHAR char(40), MOM_PROJEC char(254), METHODE char(254), EIGENAAR char(254), BEHEER char(254), OPDRACHTGE char(254), STATUS char(254), STROOMGEBI char(254), EINDJAAR char(254), OBJECTCODE char(254), KOKER_TYPE char(254), BOOR_DATUM char(254), BRO_ID char(254), TOETSING_O double, TOETSING_G double, WATERAFSPR double, DAGELIJKSE double, WATERBEHEE double, WATERBEH_1 double, M_WATERST smallint, M_KLEPSCHF smallint, M_STRMSNL smallint,
      M_AFVOER smallint, M_WQL smallint
    -> Tester_7
Note: Tester: status niet opgeheven. En type is oppervlaktewater.
Tester_7
    BOOL_OP = COMPOSITE
    COMPOSITE_TEST = 1 AND 2
    TEST_CLAUSE:
      TEST @Value(STATUS) != OPGEHEVEN
      TEST @Value(SITE_TYPE) = Oppervlaktewater
    TEST_MODE = TEST
    PASSED -> GeonisBlaeuToHyDAMOConverterMeetlocatie [GeonisBlaeu_Meetlocatie]
BLAEU.GW_GFE (reader ARCGIS_LAYER_11)
    attributes: OBJECTID integer, GFEIDENT char(24), OVK_OVK_ID_AA integer, OVK_OVK_ID_AF integer, OVK_OVK_ID_BZ integer, GFEOPPVL integer, GFEOPPVL_L integer, GFESOPPV integer, GFESOPPV_L integer, GFESAFVC double, GFESAFVC_L integer, GFESAANV double, GFESAANV_L integer, GFEAFVCO double, GFEAFVCO_L integer, GFEAANCO double, GFEAANCO_L integer, GFEPKWEL float, GFENKWEL float, OSMOMSCH char(60), RICHTING float, CREATED_USER char(50), CREATED_DATE date, LAST_EDITED_USER char(50), LAST_EDITED_DATE date, GEONAUWKEURIGHEID integer, ADMINNAUWKEURIGHEID integer, BETROUWBAARHEID integer, INWINNINGSWIJZE integer, INWINNINGSDATUM date,
      BRON char(255), IDEALISATIE integer, OPMERKINGEN char(255), GEONAUWKEURIGHEID_Z integer, IWS_KWLTGEO integer, IWS_EIGENAAR char(255), GLOBALID char(38), GLOBALID_1 char(2048), GPG_GPG_ID char(2048), GAF_GAF_ID char(2048)
    -> Tester_13
Note: Tester: alleen WRIJ afwateringseenheden: OSMOMSCHR begint met "N:"
Tester_13
    BOOL_OP = OR
    COMPOSITE_TEST = 1
    TEST_CLAUSE = CASE_INSENSITIVE_TEST @Value(OSMOMSCH) BEGINS_WITH N:
    TEST_MODE = TEST
    PASSED -> AttributeManager_13
AttributeManager_13
    ATTR_TABLE:
      RENAME_SET_VALUE GLOBALID
      RENAME_SET_VALUE GLOBALID_1 > GLOBALID_GFE
    -> GeonisBlaeuToHyDAMOConverterAfvoergebiedAanvoergebied [GeonisBlaeu_Afwateringsgebied]

Bookmark: Omzetten Geonis Blaeu naar HyDAMO
GeonisBlaeuToHyDAMOConverterDuikerSifonHevel
    CREATED_DATE = @Value(CREATED_DATE)
    GLOBALID_KDU = @Value(GLOBALID_KDU)
    LAST_EDITED_DATE = @Value(LAST_EDITED_DATE)
    administratiefgebied = 12
    bochtEnKnikverlies = 0
    breedteOpening = @Value(KDUBREED)
    breedte_temp = @Value(KDUBUIS)
    code = @Value(KDUIDENT)
    hoogteBinnenOnderkantBene = @Value(KDUBOKBE)
    hoogteBinnenOnderkantBove = @Value(KDUBOKBO)
    hoogteOpening = @Value(KDUHGA1)
    hyperlink = @Value(IWS_HYPERLINK)
    indPeilRegulPeilScheidend = @Value(KDUAFSBO)
    indPeilregulPeilScheidend_temp = @Value(KDUAFSBE)
    intreeverlies = 1
    lengte = @Value(KDULENGT)
    ruwheid = @Value(XXXMATER)
    statusObject = @Value(KWKSTATU)
    typeKruising = 3
    typeRuwheid = 4
    uittreeverlies = 0.7
    vormKoker = @Value(KDUVORM)
    HyDAMO_DuikerSifonHevel -> HyDAMOHDBcreatorDuikerSifonHevel [HyDAMO_Duikersifonhevel]
GeonisBlaeuToHyDAMOConverterHydroobject
    CREATED_DATE = @Value(CREATED_DATE)
    GLOBALID_LV = @Value(GLOBALID_LV)
    LAST_EDITED_DATE = @Value(LAST_EDITED_DATE)
    administratiefgebied = 12
    categorieOppwaterlichaam = @Value(IWS_CATEGORIEEN)
    code = @Value(OVKIDENT)
    naam = @Value(OWANAAM)
    ruwheidHoog = 15
    ruwheidLaag = 25
    statusObject = @Value(KWKSTATU)
    typeRuwheid = 4
    HyDAMO_Hydroobject -> HyDAMOHDBCreatorHydroobject [HyDAMO_Hydroobject]
GeonisBlaeuToHyDAMOConverterMetingProfiel
    CODE_MPL = @Value(GLOBALID_MPL)
    CREATED_DATE_LV = @Value(CREATED_DATE)
    CREATED_DATE_MPL = @Value(CREATED_DATE_MPL)
    DATUMTIJDINWINNING = @Value(DATUMTIJDINWINNING)
    GLOBALID_LV = @Value(GLOBALID_LV)
    GLOBALID_MPL = @Value(GLOBALID_MPL)
    GLOBALID_MPP = @Value(GLOBALID_MPP)
    KWKSTATU_LV = @Value(KWKSTATU)
    LAST_EDITED_DATE_LV = @Value(LAST_EDITED_DATE)
    LAST_EDITED_DATE_MPL = @Value(LAST_EDITED_DATE_MPL)
    OVKIDENT = @Value(OVKIDENT)
    SOORTMEETPUNT = @Value(SOORTMEETPUNT)
    administratiefgebied = 12
    codeVolgnummer = @Value(CODEVOLGNUMMER)
    hydroobjectID_LV = @Value(OVKIDENT)
    metingprofiellijnID = @Value(METINGPROFIELLIJNID)
    ruwheidHoog = 15
    ruwheidLaag = 25
    soortProfiel = @Value(SOORTPROFIEL)
    statusObject_MPL = @Value(STATUS_MPL)
    statusObject_MPP = 3
    stuwID = @Value(KSTIDENT)
    typeBodem_LV = 1
    typeBodem_MPP = @Value(PROFIELWEERGAVE)
    typeRuwheid = 4
    HyDAMO_MetingProfielPunt -> HyDAMOHDBCreatorMetingProfielPunt
    HyDAMO_MetingProfielLijn -> HyDAMOHDBCreatorMetingProfielLijn
GeonisBlaeuToHyDAMOConverterStuw
    CREATED_DATE = @Value(CREATED_DATE)
    CREATED_DATE_a = @Value(CREATED_DATE)
    CREATED_DATE_d = @Value(CREATED_DATE)
    LAST_EDITED_DATE = @Value(LAST_EDITED_DATE)
    LAST_EDITED_DATE_a = @Value(LAST_EDITED_DATE)
    LAST_EDITED_DATE_d = @Value(LAST_EDITED_DATE)
    Zomerstreefpeil = @Value(IWS_KSTZMRPL)
    aantal = @Value(KSTAANT)
    administratiefgebied = 12
    administratiefgebied_a = 12
    administratiefgebied_d = 12
    afvoerCoefficient = 1
    afvoerCoefficient_a = 1
    afvoerCoefficient_d = 1
    breedte_a = @Value(KSTDSBRE)
    code = @Value(KSTIDENT)
    code_a = @Value(KSTIDENT)
    code_d = @Value(KSTIDENT)
    codegerelateerdobject_a = @Value(KSTIDENT)
    codegerelateerdobject_d = @Value(KSTIDENT)
    doorstroomlengte_d = 0.05
    globalID = @Value(GLOBALID_KST)
    hoogsteDoorstroombreedte_d = @Value(KSTDSBRE)
    hoogsteDoorstroomhoogte_d = @Value(KSTMAXKR)
    hoogteConstructie = @Value(KSTHOOGT)
    hoogte_a = @Value(KSTMAXKR)
    hoogte_a_temp = @Value(KSTMIKHO)
    hyperlink = @Value(IWS_HYPERLINK)
    kruinbreedte = @Value(KSTKRUBR)
    laagsteDoorstroombreedte_d = @Value(KSTDSBRE)
    laagsteDoorstroomhoogte_d = @Value(KSTMIKHO)
    maximaleHoogteBovenkant_a = @Value(KSTMAXKR)
    minimaleHoogteBovenkant_a = @Value(KSTMIKHO)
    naam = @Value(KWKNAAM)
    overlaatOnderlaat = 1
    richting = @Value(RICHTING)
    soortAfsluitmiddel_a = @Value(KSTSOORT)
    soortRegelbaarheid = @Value(KSTREGEL)
    soortRegelbaarheid_a = @Value(KSTREGEL)
    soortStuw = @Value(KSTSOORT)
    statusObject = @Value(KWKSTATU)
    statusObject_a = @Value(KWKSTATU)
    statusObject_d = @Value(KWKSTATU)
    vormOpening_d = @Value(KSTKRVRM)
    HyDAMO_Stuw -> HyDAMOHDBcreatorStuw [HyDAMO_Stuw]
    HyDAMO_Afsluitmiddel -> HyDAMOHDBcreatorAfsluitmiddel [HyDAMO_Afsluitmiddel]
    HyDAMO_Doorstroomopening -> HyDAMOHDBcreatorDoorstroomopening [HyDAMO_Doorstroomopening]
GeonisBlaeuToHyDAMOConverterAfsluitmiddel
    CREATED_DATE = @Value(CREATED_DATE)
    LAST_EDITED_DATE = @Value(LAST_EDITED_DATE)
    administratiefgebied = 12
    afvoerCoefficient = 1
    breedte_d = @Value(KDUBREED)
    code_af = @Value(KWKIDENT)
    code_d = @Value(KDUIDENT)
    globalID_AKN = @Value(GLOBALID_AKN)
    globalID_KDU = @Value(GLOBALID_KDU)
    hoogte_d = @Value(KDUHGA1)
    hoogtebinnenonderkantben_d = @Value(KDUBOKBE)
    hoogtebinnenonderkantbov_d = @Value(KDUBOKBO)
    soortAfsluitmiddel = @Value(KWKAFSL1)
    soortRegelbaarheid = @Value(WRIJ_TYPE_REGELBAARHEID)
    statusObject = @Value(KWKSTATU)
    vorm_duiker = @Value(KDUVORM)
    zoek_afstand = 0.5
    HyDAMO_Afsluitmiddel -> HyDAMOHDBcreatorAfsluitmiddel [HyDAMO_Afsluitmiddel]
GeonisBlaeuToHyDAMOConverterPomp: GeonisBlaeuToHyDAMOConverterPomp_2
    CREATED_DATE = @Value(CREATED_DATE)
    LAST_EDITED_DATE = @Value(LAST_EDITED_DATE)
    aantal = @Value(KGMAAPOM)
    administratiefgebied = 12
    code = @Value(KGMIDENT)
    code_g = @Value(KGMIDENT)
    gemaalID = @Value(KGMIDENT)
    globalID = @Value(GLOBALID_KGM)
    hyperlink_g = @Value(IWS_HYPERLINK)
    maximaleCapaciteit = @Value(KGMMACAP)
    naam_g = @Value(OSMOMSCH)
    pomprichting = @Value(KGMFUNC)
    statusObject = @Value(KWKSTATU)
    HyDAMO_Gemaal -> HyDAMOHDBcreatorGemaal [HyDAMO_Gemaal]
    HyDAMO_Pomp -> HyDAMOHDBcreatorPomp [HyDAMO_Pomp]
GeonisBlaeuToHyDAMOConverterBrug
    CREATED_DATE = @Value(CREATED_DATE)
    LAST_EDITED_DATE = @Value(LAST_EDITED_DATE)
    administratiefgebied = 12
    code = @Value(KBRIDENT)
    globalID = @Value(GLOBALID_KBR)
    hoogteBovenzijde = @Value(KBRHOBB)
    hoogteOnderzijde = @Value(KBRHOBO)
    hoogteOnderzijde_temp = @Value(KBRHOBE)
    intreeverlies = 0
    lengte = @Value(KBRLENGT)
    naam = @Value(KWKNAAM)
    ruwheid = 34
    statusObject = @Value(KWKSTATU)
    typeRuwheid = 4
    uittreeverlies = 0
    HyDAMO_Brug -> HyDAMOHDBcreatorBrug [HyDAMO_Brug]
GeonisBlaeuToHyDAMOConverterBodemval
    CREATED_DATE = @Value(CREATED_DATE)
    LAST_EDITED_DATE = @Value(LAST_EDITED_DATE)
    administratiefgebied = 12
    bodemhoogteBenedenstrooms = @Value(KBVHOBE)
    bodemhoogteBovenstrooms = @Value(KBVHOBO)
    code = @Value(KBVIDENT)
    globalID = @Value(GLOBALID_KBV)
    naam = @Value(KWKNAAM)
    statusObject = @Value(KWKSTATU)
    HyDAMO_Bodemval -> HyDAMOHDBcreatorBodemval [HyDAMO_Bodemval]
GeonisBlaeuToHyDAMOConverterMeetlocatie [off]
    administratiefgebied = 12
    code = @Value(SITE_NO)
    metingAfvoer = @Value(SITE_NAME)
    metingKlepOfSchuifstand = 3
    metingStroomsnelheid = 3
    metingWaterkwaliteit = 3
    metingWaterstand = 3
    naam = @Value(SITE_NAME)
    statusObject = @Value(STATUS)
    HyDAMO_Meetlocatie -> HyDAMOHDBcreatorMeetlocatie [HyDAMO_Meetlocatie]
GeonisBlaeuToHyDAMOConverterAfvoergebiedAanvoergebied
    CREATED_DATE = @Value(CREATED_DATE)
    LAST_EDITED_DATE = @Value(LAST_EDITED_DATE)
    administratiefgebied = 12
    code = @Value(GFEIDENT)
    globalID = @Value(GLOBALID_GFE)
    lateraleknoopID = ntb
    naam = @Value(GFEIDENT)
    oppervlakte = @Value(GFEOPPVL)
    soortAfvoerAanvoergebied = 5
    statusObject = 3
    HyDAMO_AfvoergebiedAanvoergebied -> HyDAMOHDBcreatorAfvoergebiedAanvoergebied [HyDAMO_AanvoergebiedAfvoergebied]

Bookmark: Controle HyDAMO en klaarzetten database voor upload naar NHI hydamo database
HyDAMOHDBcreatorDuikerSifonHevel
    CREATED_DATE = @Value(CREATED_DATE)
    LAST_EDITED_DATE = @Value(LAST_EDITED_DATE)
    administratiefgebied = @Value(administratiefgebied)
    bochtEnKnikverlies = @Value(bochtEnKnikverlies)
    breedteOpening = @Value(breedteOpening)
    code = @Value(code)
    format = gpkg gdb gml
    globalID = @Value(globalID)
    hoogteBinnenOnderkantBene = @Value(hoogteBinnenOnderkantBene)
    hoogteBinnenOnderkantBove = @Value(hoogteBinnenOnderkantBove)
    hoogteOpening = @Value(hoogteOpening)
    hyperlink = @Value(hyperlink)
    indPeilRegulPeilScheidend = @Value(indPeilRegulPeilScheidend)
    intreeverlies = @Value(intreeverlies)
    lengte = @Value(lengte)
    outputfolder = G:\GIS WATERSYSTEEM\HyDAMO\FME\output_v2021
    ruwheid = @Value(ruwheid)
    statusObject = @Value(statusObject)
    typeKruising = @Value(typeKruising)
    typeRuwheid = @Value(typeRuwheid)
    uittreeverlies = @Value(uittreeverlies)
    vormKoker = @Value(vormKoker)
HyDAMOHDBCreatorHydroobject
    CREATED_DATE = @Value(CREATED_DATE)
    LAST_EDITED_DATE = @Value(LAST_EDITED_DATE)
    administratiefgebied = @Value(administratiefgebied)
    categorieOppwaterlichaam = @Value(categorieOppwaterlichaam)
    code = @Value(code)
    format = gdb gpkg gml
    globalID = @Value(globalID)
    hyperlink = @Value(hyperlink)
    naam = @Value(naam)
    outputfolder = G:\GIS WATERSYSTEEM\HyDAMO\FME\output_v2021
    ruwheidHoog = @Value(ruwheidHoog)
    ruwheidLaag = @Value(ruwheidLaag)
    statusObject = @Value(statusObject)
    typeRuwheid = @Value(typeRuwheid)
HyDAMOHDBCreatorMetingProfielPunt
    CREATED_DATE = @Value(CREATED_DATE)
    LAST_EDITED_DATE = @Value(LAST_EDITED_DATE)
    administratiefgebied = @Value(administratiefgebied)
    code = @Value(code)
    codeVolgnummer = @Value(codeVolgnummer)
    format = gpkg gdb gml
    globalID = @Value(globalID)
    metingprofiellijnID = @Value(metingprofiellijnID)
    outputfolder = G:\GIS WATERSYSTEEM\HyDAMO\FME\output_v2021
    ruwheidHoog = @Value(ruwheidHoog)
    ruwheidLaag = @Value(ruwheidLaag)
    soortMeetpunt = @Value(soortMeetpunt)
    statusObject = @Value(statusObject)
    typeBodem = @Value(typeBodem)
    typeRuwheid = @Value(typeRuwheid)
HyDAMOHDBCreatorMetingProfielLijn
    CREATED_DATE = @Value(CREATED_DATE)
    LAST_EDITED_DATE = @Value(LAST_EDITED_DATE)
    administratiefgebied = 12
    bodemvalID = @Value(bodemvalID)
    brugID = @Value(brugID)
    code = @Value(code)
    format = gdb gpkg gml
    globalID = @Value(globalID)
    grondwaterkoppellijnID = @Value(grondwaterkoppellijnID)
    hydroobjectID = @Value(hydroobjectID)
    outputfolder = G:\GIS WATERSYSTEEM\HyDAMO\FME\output_v2021
    soortProfiel = @Value(soortProfiel)
    statusObject = @Value(statusObject)
    stuwID = @Value(stuwID)
HyDAMOHDBcreatorStuw
    CREATED_DATE = @Value(CREATED_DATE)
    LAST_EDITED_DATE = @Value(LAST_EDITED_DATE)
    administratiefgebied = @Value(administratiefgebied)
    afvoerCoefficient = @Value(afvoerCoefficient)
    code = @Value(code)
    format = gml gdb gpkg
    globalID = @Value(globalID)
    hoogteConstructie = @Value(hoogteConstructie)
    hyperlink = @Value(hyperlink)
    kruinbreedte = @Value(kruinbreedte)
    naam = @Value(naam)
    outputfolder = G:\GIS WATERSYSTEEM\HyDAMO\FME\output_v2021
    richting = @Value(richting)
    soortRegelbaarheid = @Value(soortRegelbaarheid)
    soortStuw = @Value(soortStuw)
    statusObject = @Value(statusObject)
HyDAMOHDBcreatorDoorstroomopening
    CREATED_DATE = @Value(CREATED_DATE)
    LAST_EDITED_DATE = @Value(LAST_EDITED_DATE)
    Zomerstreefpeil = @Value(zomerstreefpeil)
    administratiefgebied = @Value(administratiefgebied)
    afvoerCoefficient = @Value(afvoerCoefficient)
    code = @Value(code)
    doorstroomlengte = @Value(doorstroomlengte)
    format = gdb gml gpkg
    hoogsteDoorstroombreedte = @Value(hoogsteDoorstroombreedte)
    hoogsteDoorstroomhoogte = @Value(hoogsteDoorstroomhoogte)
    laagsteDoorstroombreedte = @Value(laagsteDoorstroombreedte)
    laagsteDoorstroomhoogte = @Value(laagsteDoorstroomhoogte)
    outputfolder = G:\GIS WATERSYSTEEM\HyDAMO\FME\output_v2021
    statusObject = @Value(statusObject)
    stuwID = @Value(stuwID)
    vormOpening = @Value(vormOpening)
HyDAMOHDBcreatorAfsluitmiddel
    CREATED_DATE = @Value(CREATED_DATE)
    LAST_EDITED_DATE = @Value(LAST_EDITED_DATE)
    Zomerstreefpeil = @Value(zomerstreefpeil)
    administratiefgebied = @Value(administratiefgebied)
    afvoerCoefficient = @Value(afvoerCoefficient)
    breedte = @Value(breedte)
    code = @Value(code)
    doorstroomopeningID = @Value(doorstroomopeningID)
    duikersifonhevelID = @Value(duikersifonhevelID)
    format = gdb gml gpkg
    globalID = @Value(globalID)
    hoogte = @Value(hoogte)
    maximaleHoogteBovenkant = @Value(maximaleHoogteBovenkant)
    minimaleHoogteBovenkant = @Value(minimaleHoogteBovenkant)
    outputfolder = G:\GIS WATERSYSTEEM\HyDAMO\FME\output_v2021
    overlaatOnderlaat = @Value(overlaatOnderlaat)
    soortAfsluitmiddel = @Value(soortAfsluitmiddel)
    soortRegelbaarheid = @Value(soortRegelbaarheid)
    statusObject = @Value(statusObject)
HyDAMOHDBcreatorGemaal
    CREATED_DATE = @Value(CREATED_DATE)
    LAST_EDITED_DATE = @Value(LAST_EDITED_DATE)
    administratiefgebied = @Value(administratiefgebied)
    code = @Value(code)
    format = gml gdb gpkg
    globalID = @Value(globalID)
    hyperlink = @Value(hyperlink)
    naam = @Value(naam)
    outputfolder = G:\GIS WATERSYSTEEM\HyDAMO\FME\output_v2021
    statusObject = @Value(statusObject)
HyDAMOHDBcreatorPomp
    CREATED_DATE = @Value(CREATED_DATE)
    LAST_EDITED_DATE = @Value(LAST_EDITED_DATE)
    administratiefgebied = @Value(administratiefgebied)
    code = @Value(code)
    format = gml gdb gpkg
    gemaalID = @Value(gemaalID)
    maximaleCapaciteit = @Value(maximaleCapaciteit)
    outputfolder = G:\GIS WATERSYSTEEM\HyDAMO\FME\output_v2021
    pompcurve = @Value(pompcurve)
    pomprichting = @Value(pomprichting)
    statusObject = @Value(statusObject)
HyDAMOHDBcreatorBrug
    CREATED_DATE = @Value(CREATED_DATE)
    LAST_EDITED_DATE = @Value(LAST_EDITED_DATE)
    administratiefgebied = @Value(administratiefgebied)
    code = @Value(code)
    format = gml gdb gpkg
    globalID = @Value(globalID)
    hoogteBovenzijde = @Value(hoogteBovenzijde)
    hoogteOnderzijde = @Value(hoogteOnderzijde)
    hyperlink = @Value(hyperlink)
    intreeverlies = @Value(intreeverlies)
    lengte = @Value(lengte)
    naam = @Value(naam)
    outputfolder = G:\GIS WATERSYSTEEM\HyDAMO\FME\output_v2021
    ruwheid = @Value(ruwheid)
    statusObject = @Value(statusObject)
    typeRuwheid = @Value(typeRuwheid)
    uittreeverlies = @Value(uittreeverlies)
HyDAMOHDBcreatorBodemval
    CREATED_DATE = @Value(CREATED_DATE)
    LAST_EDITED_DATE = @Value(LAST_EDITED_DATE)
    administratiefgebied = @Value(administratiefgebied)
    bodemhoogteBenedenstrooms = @Value(bodemhoogteBenedenstrooms)
    bodemhoogteBovenstrooms = @Value(bodemhoogteBovenstrooms)
    code = @Value(code)
    format = gml gdb gpkg
    globalID = @Value(globalID)
    hyperlink = @Value(hyperlink)
    naam = @Value(naam)
    outputfolder = G:\GIS WATERSYSTEEM\HyDAMO\FME\output_v2021
    statusObject = @Value(statusObject)
HyDAMOHDBcreatorMeetlocatie [off]
    CREATED_DATE = @Value(CREATED_DATE)
    LAST_EDITED_DATE = @Value(LAST_EDITED_DATE)
    administratiefgebied = @Value(administratiefgebied)
    code = @Value(code)
    format = ffs gml
    hyperlink = @Value(hyperlink)
    metingAfvoer = @Value(metingAfvoer)
    metingKlepOfSchuifstand = @Value(metingKlepOfSchuifstand)
    metingStroomsnelheid = @Value(metingStroomsnelheid)
    metingWaterkwaliteit = @Value(metingWaterkwaliteit)
    metingWaterstand = @Value(metingWaterstand)
    naam = @Value(naam)
    outputfolder = G:\GIS WATERSYSTEEM\HyDAMO\FME\output_v2020
    statusObject = @Value(statusObject)
HyDAMOHDBcreatorAfvoergebiedAanvoergebied
    CREATED_DATE = @Value(CREATED_DATE)
    LAST_EDITED_DATE = @Value(LAST_EDITED_DATE)
    administratiefgebied = @Value(administratiefgebied)
    code = @Value(code)
    format = gdb gml gpkg
    globalID = @Value(globalID)
    hyperlink = @Value(hyperlink)
    lateraleknoopID = @Value(lateraleknoopID)
    naam = @Value(naam)
    oppervlakte = @Value(oppervlakte)
    ordeCode = @Value(ordeCode)
    outputfolder = G:\GIS WATERSYSTEEM\HyDAMO\FME\output_v2021
    soortAfvoerAanvoergebied = @Value(soortAfvoerAanvoergebied)
    statusObject = @Value(statusObject)
